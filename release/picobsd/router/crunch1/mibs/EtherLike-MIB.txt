EtherLike-MIB DEFINITIONS ::= BEGIN

IMPORTS
    ifEntry, ifIndex
        FROM IF-MIB
    OBJECT-GROUP, MODULE-COMPLIANCE
        FROM SNMPv2-CONF
    PhysAddress, TEXTUAL-CONVENTION
        FROM SNMPv2-TC
    transmission, mib-2, Integer32, Gauge32, Counter32, OBJECT-TYPE, MODULE-IDENTITY
        FROM SNMPv2-SMI;

etherMIB MODULE-IDENTITY
    LAST-UPDATED "9402030400Z"
    ORGANIZATION "IETF Interfaces MIB Working Group"
    CONTACT-INFO
                 "Frank Kastenholz

      Postal: FTP Software
              2 High Street
              North Andover, MA 01845
              US

         Tel: +1 508 685 4000
      E-Mail: kasten@ftp.com"
    ::= { mib-2  35 }

etherMIBObjects ::= { etherMIB  1 }

dot3 ::= { transmission  7 }

dot3StatsTable OBJECT-TYPE
    SYNTAX     SEQUENCE OF Dot3StatsEntry
    MAX-ACCESS not-accessible
    STATUS     current
    ::= { dot3  2 }

dot3StatsEntry OBJECT-TYPE
    SYNTAX     Dot3StatsEntry
    MAX-ACCESS not-accessible
    STATUS     current
    INDEX      { dot3StatsIndex }
    ::= { dot3StatsTable  1 }

Dot3StatsEntry ::=
    SEQUENCE {
        dot3StatsIndex
            INTEGER,

        dot3StatsAlignmentErrors
            Counter32,

        dot3StatsFCSErrors
            Counter32,

        dot3StatsSingleCollisionFrames
            Counter32,

        dot3StatsMultipleCollisionFrames
            Counter32,

        dot3StatsSQETestErrors
            Counter32,

        dot3StatsDeferredTransmissions
            Counter32,

        dot3StatsLateCollisions
            Counter32,

        dot3StatsExcessiveCollisions
            Counter32,

        dot3StatsInternalMacTransmitErrors
            Counter32,

        dot3StatsCarrierSenseErrors
            Counter32,

        dot3StatsFrameTooLongs
            Counter32,

        dot3StatsInternalMacReceiveErrors
            Counter32,

        dot3StatsEtherChipSet
            OBJECT IDENTIFIER
    }

dot3StatsIndex OBJECT-TYPE
    SYNTAX     INTEGER
    MAX-ACCESS read-only
    STATUS     current
    ::= { dot3StatsEntry  1 }

dot3StatsAlignmentErrors OBJECT-TYPE
    SYNTAX     Counter32
    MAX-ACCESS read-only
    STATUS     current
    REFERENCE
        "IEEE 802.3 Layer Management"
    ::= { dot3StatsEntry  2 }

dot3StatsFCSErrors OBJECT-TYPE
    SYNTAX     Counter32
    MAX-ACCESS read-only
    STATUS     current
    REFERENCE
        "IEEE 802.3 Layer Management"
    ::= { dot3StatsEntry  3 }

dot3StatsSingleCollisionFrames OBJECT-TYPE
    SYNTAX     Counter32
    MAX-ACCESS read-only
    STATUS     current
    REFERENCE
        "IEEE 802.3 Layer Management"
    ::= { dot3StatsEntry  4 }

dot3StatsMultipleCollisionFrames OBJECT-TYPE
    SYNTAX     Counter32
    MAX-ACCESS read-only
    STATUS     current
    REFERENCE
        "IEEE 802.3 Layer Management"
    ::= { dot3StatsEntry  5 }

dot3StatsSQETestErrors OBJECT-TYPE
    SYNTAX     Counter32
    MAX-ACCESS read-only
    STATUS     current
    REFERENCE
        "ANSI/IEEE Std 802.3-1985 Carrier Sense
         Multiple Access with Collision Detection Access
         Method and Physical Layer Specifications"
    ::= { dot3StatsEntry  6 }

dot3StatsDeferredTransmissions OBJECT-TYPE
    SYNTAX     Counter32
    MAX-ACCESS read-only
    STATUS     current
    REFERENCE
        "IEEE 802.3 Layer Management"
    ::= { dot3StatsEntry  7 }

dot3StatsLateCollisions OBJECT-TYPE
    SYNTAX     Counter32
    MAX-ACCESS read-only
    STATUS     current
    REFERENCE
        "IEEE 802.3 Layer Management"
    ::= { dot3StatsEntry  8 }

dot3StatsExcessiveCollisions OBJECT-TYPE
    SYNTAX     Counter32
    MAX-ACCESS read-only
    STATUS     current
    REFERENCE
        "IEEE 802.3 Layer Management"
    ::= { dot3StatsEntry  9 }

dot3StatsInternalMacTransmitErrors OBJECT-TYPE
    SYNTAX     Counter32
    MAX-ACCESS read-only
    STATUS     current
    REFERENCE
        "IEEE 802.3 Layer Management"
    ::= { dot3StatsEntry  10 }

dot3StatsCarrierSenseErrors OBJECT-TYPE
    SYNTAX     Counter32
    MAX-ACCESS read-only
    STATUS     current
    REFERENCE
        "IEEE 802.3 Layer Management"
    ::= { dot3StatsEntry  11 }

dot3StatsFrameTooLongs OBJECT-TYPE
    SYNTAX     Counter32
    MAX-ACCESS read-only
    STATUS     current
    REFERENCE
        "IEEE 802.3 Layer Management"
    ::= { dot3StatsEntry  13 }

dot3StatsInternalMacReceiveErrors OBJECT-TYPE
    SYNTAX     Counter32
    MAX-ACCESS read-only
    STATUS     current
    REFERENCE
        "IEEE 802.3 Layer Management"
    ::= { dot3StatsEntry  16 }

dot3StatsEtherChipSet OBJECT-TYPE
    SYNTAX     OBJECT IDENTIFIER
    MAX-ACCESS read-only
    STATUS     current
    ::= { dot3StatsEntry  17 }

dot3CollTable OBJECT-TYPE
    SYNTAX     SEQUENCE OF Dot3CollEntry
    MAX-ACCESS not-accessible
    STATUS     current
    ::= { dot3  5 }

dot3CollEntry OBJECT-TYPE
    SYNTAX     Dot3CollEntry
    MAX-ACCESS not-accessible
    STATUS     current
    INDEX      { ifIndex,  dot3CollCount }
    ::= { dot3CollTable  1 }

Dot3CollEntry ::=
    SEQUENCE {
        dot3CollCount
            INTEGER,

        dot3CollFrequencies
            Counter32
    }

dot3CollCount OBJECT-TYPE
    SYNTAX     INTEGER
    MAX-ACCESS not-accessible
    STATUS     current
    ::= { dot3CollEntry  2 }

dot3CollFrequencies OBJECT-TYPE
    SYNTAX     Counter32
    MAX-ACCESS read-only
    STATUS     current
    ::= { dot3CollEntry  3 }

dot3Tests ::= { dot3  6 }

dot3Errors ::= { dot3  7 }

dot3TestTdr ::= { dot3Tests  1 }

dot3TestLoopBack ::= { dot3Tests  2 }

dot3ErrorInitError ::= { dot3Errors  1 }

dot3ErrorLoopbackError ::= { dot3Errors  2 }

dot3ChipSets ::= { dot3  8 }

dot3ChipSetAMD ::= { dot3ChipSets  1 }

dot3ChipSetAMD7990 ::= { dot3ChipSetAMD  1 }

dot3ChipSetAMD79900 ::= { dot3ChipSetAMD  2 }

dot3ChipSetAMD79C940 ::= { dot3ChipSetAMD  3 }

dot3ChipSetIntel ::= { dot3ChipSets  2 }

dot3ChipSetIntel82586 ::= { dot3ChipSetIntel  1 }

dot3ChipSetIntel82596 ::= { dot3ChipSetIntel  2 }

dot3ChipSetSeeq ::= { dot3ChipSets  3 }

dot3ChipSetSeeq8003 ::= { dot3ChipSetSeeq  1 }

dot3ChipSetNational ::= { dot3ChipSets  4 }

dot3ChipSetNational8390 ::= { dot3ChipSetNational  1 }

dot3ChipSetNationalSonic ::= { dot3ChipSetNational  2 }

dot3ChipSetFujitsu ::= { dot3ChipSets  5 }

dot3ChipSetFujitsu86950 ::= { dot3ChipSetFujitsu  1 }

dot3ChipSetDigital ::= { dot3ChipSets  6 }

dot3ChipSetDigitalDC21040 ::= { dot3ChipSetDigital  1 }

etherConformance ::= { etherMIB  2 }

etherGroups ::= { etherConformance  1 }

etherCompliances ::= { etherConformance  2 }

etherCompliance MODULE-COMPLIANCE
    STATUS     current

    MANDATORY-GROUPS { etherStatsGroup }
        GROUP        etherCollisionTableGroup
    ::= { etherCompliances  1 }

etherStatsGroup OBJECT-GROUP
    OBJECTS    {
                 dot3StatsIndex,
                 dot3StatsAlignmentErrors,
                 dot3StatsFCSErrors,
                 dot3StatsSingleCollisionFrames,
                 dot3StatsMultipleCollisionFrames,
                 dot3StatsSQETestErrors,
                 dot3StatsDeferredTransmissions,
                 dot3StatsLateCollisions,
                 dot3StatsExcessiveCollisions,
                 dot3StatsInternalMacTransmitErrors,
                 dot3StatsCarrierSenseErrors,
                 dot3StatsFrameTooLongs,
                 dot3StatsInternalMacReceiveErrors,
                 dot3StatsEtherChipSet
               }
    STATUS     current
    ::= { etherGroups  1 }

etherCollisionTableGroup OBJECT-GROUP
    OBJECTS    { dot3CollCount,  dot3CollFrequencies }
    STATUS     current
    ::= { etherGroups  2 }

END
