UDP-MIB DEFINITIONS ::= BEGIN

IMPORTS
    OBJECT-GROUP, MODULE-COMPLIANCE
        FROM SNMPv2-CONF
    mib-2, IpAddress, Counter32, OBJECT-TYPE, MODULE-IDENTITY
        FROM SNMPv2-SMI;

udpMIB MODULE-IDENTITY
    LAST-UPDATED "9411010000Z"
    ORGANIZATION "IETF SNMPv2 Working Group"
    CONTACT-INFO
                 "Keith McCloghrie

          Postal: Cisco Systems, Inc.
                  170 West Tasman Drive
                  San Jose, CA  95134-1706
                  US

          Phone:  +1 408 526 5260
          Email:  kzm@cisco.com"
    REVISION     "9103310000Z"
    ::= { mib-2  50 }

udp ::= { mib-2  7 }

udpInDatagrams OBJECT-TYPE
    SYNTAX     Counter32
    MAX-ACCESS read-only
    STATUS     current
    ::= { udp  1 }

udpNoPorts OBJECT-TYPE
    SYNTAX     Counter32
    MAX-ACCESS read-only
    STATUS     current
    ::= { udp  2 }

udpInErrors OBJECT-TYPE
    SYNTAX     Counter32
    MAX-ACCESS read-only
    STATUS     current
    ::= { udp  3 }

udpOutDatagrams OBJECT-TYPE
    SYNTAX     Counter32
    MAX-ACCESS read-only
    STATUS     current
    ::= { udp  4 }

udpTable OBJECT-TYPE
    SYNTAX     SEQUENCE OF UdpEntry
    MAX-ACCESS not-accessible
    STATUS     current
    ::= { udp  5 }

udpEntry OBJECT-TYPE
    SYNTAX     UdpEntry
    MAX-ACCESS not-accessible
    STATUS     current
    INDEX      { udpLocalAddress,  udpLocalPort }
    ::= { udpTable  1 }

UdpEntry ::=
    SEQUENCE {
        udpLocalAddress
            IpAddress,

        udpLocalPort
            INTEGER
    }

udpLocalAddress OBJECT-TYPE
    SYNTAX     IpAddress
    MAX-ACCESS read-only
    STATUS     current
    ::= { udpEntry  1 }

udpLocalPort OBJECT-TYPE
    SYNTAX     INTEGER
    MAX-ACCESS read-only
    STATUS     current
    ::= { udpEntry  2 }

udpMIBConformance ::= { udpMIB  2 }

udpMIBCompliances ::= { udpMIBConformance  1 }

udpMIBGroups ::= { udpMIBConformance  2 }

udpMIBCompliance MODULE-COMPLIANCE
    STATUS     current

    MANDATORY-GROUPS { udpGroup }
    ::= { udpMIBCompliances  1 }

udpGroup OBJECT-GROUP
    OBJECTS    {
                 udpInDatagrams,
                 udpNoPorts,
                 udpInErrors,
                 udpOutDatagrams,
                 udpLocalAddress,
                 udpLocalPort
               }
    STATUS     current
    ::= { udpMIBGroups  1 }

END
