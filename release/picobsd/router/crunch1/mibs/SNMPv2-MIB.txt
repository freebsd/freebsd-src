SNMPv2-MIB DEFINITIONS ::= BEGIN

IMPORTS
    NOTIFICATION-GROUP, OBJECT-GROUP, MODULE-COMPLIANCE
        FROM SNMPv2-CONF
    TimeStamp, TestAndIncr, DisplayString
        FROM SNMPv2-TC
    mib-2, snmpModules, Counter32, TimeTicks, NOTIFICATION-TYPE, OBJECT-TYPE,
    MODULE-IDENTITY
        FROM SNMPv2-SMI;

snmpMIB MODULE-IDENTITY
    LAST-UPDATED "9511090000Z"
    ORGANIZATION "IETF SNMPv2 Working Group"
    CONTACT-INFO
                 "Marshall T. Rose

          Postal: Dover Beach Consulting, Inc.
                  420 Whisman Court
                  Mountain View, CA  94043-2186
                  US

             Tel: +1 415 968 1052

          E-mail: mrose@dbc.mtview.ca.us"
    REVISION     "9304010000Z"
    ::= { snmpModules  1 }

snmpMIBObjects ::= { snmpMIB  1 }

system ::= { mib-2  1 }

sysDescr OBJECT-TYPE
    SYNTAX     DisplayString
    MAX-ACCESS read-only
    STATUS     current
    ::= { system  1 }

sysObjectID OBJECT-TYPE
    SYNTAX     OBJECT IDENTIFIER
    MAX-ACCESS read-only
    STATUS     current
    ::= { system  2 }

sysUpTime OBJECT-TYPE
    SYNTAX     TimeTicks
    MAX-ACCESS read-only
    STATUS     current
    ::= { system  3 }

sysContact OBJECT-TYPE
    SYNTAX     DisplayString
    MAX-ACCESS read-write
    STATUS     current
    ::= { system  4 }

sysName OBJECT-TYPE
    SYNTAX     DisplayString
    MAX-ACCESS read-write
    STATUS     current
    ::= { system  5 }

sysLocation OBJECT-TYPE
    SYNTAX     DisplayString
    MAX-ACCESS read-write
    STATUS     current
    ::= { system  6 }

sysServices OBJECT-TYPE
    SYNTAX     INTEGER
    MAX-ACCESS read-only
    STATUS     current
    ::= { system  7 }

sysORLastChange OBJECT-TYPE
    SYNTAX     TimeStamp
    MAX-ACCESS read-only
    STATUS     current
    ::= { system  8 }

sysORTable OBJECT-TYPE
    SYNTAX     SEQUENCE OF SysOREntry
    MAX-ACCESS not-accessible
    STATUS     current
    ::= { system  9 }

sysOREntry OBJECT-TYPE
    SYNTAX     SysOREntry
    MAX-ACCESS not-accessible
    STATUS     current
    INDEX      { sysORIndex }
    ::= { sysORTable  1 }

SysOREntry ::=
    SEQUENCE {
        sysORIndex
            INTEGER,

        sysORID
            OBJECT IDENTIFIER,

        sysORDescr
            DisplayString,

        sysORUpTime
            TimeStamp
    }

sysORIndex OBJECT-TYPE
    SYNTAX     INTEGER
    MAX-ACCESS not-accessible
    STATUS     current
    ::= { sysOREntry  1 }

sysORID OBJECT-TYPE
    SYNTAX     OBJECT IDENTIFIER
    MAX-ACCESS read-only
    STATUS     current
    ::= { sysOREntry  2 }

sysORDescr OBJECT-TYPE
    SYNTAX     DisplayString
    MAX-ACCESS read-only
    STATUS     current
    ::= { sysOREntry  3 }

sysORUpTime OBJECT-TYPE
    SYNTAX     TimeStamp
    MAX-ACCESS read-only
    STATUS     current
    ::= { sysOREntry  4 }

snmp ::= { mib-2  11 }

snmpInPkts OBJECT-TYPE
    SYNTAX     Counter32
    MAX-ACCESS read-only
    STATUS     current
    ::= { snmp  1 }

snmpInBadVersions OBJECT-TYPE
    SYNTAX     Counter32
    MAX-ACCESS read-only
    STATUS     current
    ::= { snmp  3 }

snmpInBadCommunityNames OBJECT-TYPE
    SYNTAX     Counter32
    MAX-ACCESS read-only
    STATUS     current
    ::= { snmp  4 }

snmpInBadCommunityUses OBJECT-TYPE
    SYNTAX     Counter32
    MAX-ACCESS read-only
    STATUS     current
    ::= { snmp  5 }

snmpInASNParseErrs OBJECT-TYPE
    SYNTAX     Counter32
    MAX-ACCESS read-only
    STATUS     current
    ::= { snmp  6 }

snmpEnableAuthenTraps OBJECT-TYPE
    SYNTAX     INTEGER {
                 enabled(1),
                 disabled(2)
               }
    MAX-ACCESS read-write
    STATUS     current
    ::= { snmp  30 }

snmpSilentDrops OBJECT-TYPE
    SYNTAX     Counter32
    MAX-ACCESS read-only
    STATUS     current
    ::= { snmp  31 }

snmpProxyDrops OBJECT-TYPE
    SYNTAX     Counter32
    MAX-ACCESS read-only
    STATUS     current
    ::= { snmp  32 }

snmpTrap ::= { snmpMIBObjects  4 }

snmpTrapOID OBJECT-TYPE
    SYNTAX     OBJECT IDENTIFIER
    MAX-ACCESS accessible-for-notify
    STATUS     current
    ::= { snmpTrap  1 }

snmpTrapEnterprise OBJECT-TYPE
    SYNTAX     OBJECT IDENTIFIER
    MAX-ACCESS accessible-for-notify
    STATUS     current
    ::= { snmpTrap  3 }

snmpTraps ::= { snmpMIBObjects  5 }

coldStart NOTIFICATION-TYPE
    STATUS     current
    ::= { snmpTraps  1 }

warmStart NOTIFICATION-TYPE
    STATUS     current
    ::= { snmpTraps  2 }

authenticationFailure NOTIFICATION-TYPE
    STATUS     current
    ::= { snmpTraps  5 }

snmpSet ::= { snmpMIBObjects  6 }

snmpSetSerialNo OBJECT-TYPE
    SYNTAX     TestAndIncr
    MAX-ACCESS read-write
    STATUS     current
    ::= { snmpSet  1 }

snmpMIBConformance ::= { snmpMIB  2 }

snmpMIBCompliances ::= { snmpMIBConformance  1 }

snmpMIBGroups ::= { snmpMIBConformance  2 }

snmpBasicCompliance MODULE-COMPLIANCE
    STATUS     current

    MANDATORY-GROUPS {
                             snmpGroup,
                             snmpSetGroup,
                             systemGroup,
                             snmpBasicNotificationsGroup
                           }
        GROUP        snmpCommunityGroup
    ::= { snmpMIBCompliances  2 }

snmpGroup OBJECT-GROUP
    OBJECTS    {
                 snmpInPkts,
                 snmpInBadVersions,
                 snmpInASNParseErrs,
                 snmpSilentDrops,
                 snmpProxyDrops,
                 snmpEnableAuthenTraps
               }
    STATUS     current
    ::= { snmpMIBGroups  8 }

snmpCommunityGroup OBJECT-GROUP
    OBJECTS    { snmpInBadCommunityNames,  snmpInBadCommunityUses }
    STATUS     current
    ::= { snmpMIBGroups  9 }

snmpSetGroup OBJECT-GROUP
    OBJECTS    { snmpSetSerialNo }
    STATUS     current
    ::= { snmpMIBGroups  5 }

systemGroup OBJECT-GROUP
    OBJECTS    {
                 sysDescr,
                 sysObjectID,
                 sysUpTime,
                 sysContact,
                 sysName,
                 sysLocation,
                 sysServices,
                 sysORLastChange,
                 sysORID,
                 sysORUpTime,
                 sysORDescr
               }
    STATUS     current
    ::= { snmpMIBGroups  6 }


snmpOutPkts OBJECT-TYPE
    SYNTAX     Counter32
    MAX-ACCESS read-only
    STATUS     obsolete
    ::= { snmp  2 }

snmpInTooBigs OBJECT-TYPE
    SYNTAX     Counter32
    MAX-ACCESS read-only
    STATUS     obsolete
    ::= { snmp  8 }

snmpInNoSuchNames OBJECT-TYPE
    SYNTAX     Counter32
    MAX-ACCESS read-only
    STATUS     obsolete
    ::= { snmp  9 }

snmpInBadValues OBJECT-TYPE
    SYNTAX     Counter32
    MAX-ACCESS read-only
    STATUS     obsolete
    ::= { snmp  10 }

snmpInReadOnlys OBJECT-TYPE
    SYNTAX     Counter32
    MAX-ACCESS read-only
    STATUS     obsolete
    ::= { snmp  11 }

snmpInGenErrs OBJECT-TYPE
    SYNTAX     Counter32
    MAX-ACCESS read-only
    STATUS     obsolete
    ::= { snmp  12 }

snmpInTotalReqVars OBJECT-TYPE
    SYNTAX     Counter32
    MAX-ACCESS read-only
    STATUS     obsolete
    ::= { snmp  13 }

snmpInTotalSetVars OBJECT-TYPE
    SYNTAX     Counter32
    MAX-ACCESS read-only
    STATUS     obsolete
    ::= { snmp  14 }

snmpInGetRequests OBJECT-TYPE
    SYNTAX     Counter32
    MAX-ACCESS read-only
    STATUS     obsolete
    ::= { snmp  15 }

snmpInGetNexts OBJECT-TYPE
    SYNTAX     Counter32
    MAX-ACCESS read-only
    STATUS     obsolete
    ::= { snmp  16 }

snmpInSetRequests OBJECT-TYPE
    SYNTAX     Counter32
    MAX-ACCESS read-only
    STATUS     obsolete
    ::= { snmp  17 }

snmpInGetResponses OBJECT-TYPE
    SYNTAX     Counter32
    MAX-ACCESS read-only
    STATUS     obsolete
    ::= { snmp  18 }

snmpInTraps OBJECT-TYPE
    SYNTAX     Counter32
    MAX-ACCESS read-only
    STATUS     obsolete
    ::= { snmp  19 }

snmpOutTooBigs OBJECT-TYPE
    SYNTAX     Counter32
    MAX-ACCESS read-only
    STATUS     obsolete
    ::= { snmp  20 }

snmpOutNoSuchNames OBJECT-TYPE
    SYNTAX     Counter32
    MAX-ACCESS read-only
    STATUS     obsolete
    ::= { snmp  21 }

snmpOutBadValues OBJECT-TYPE
    SYNTAX     Counter32
    MAX-ACCESS read-only
    STATUS     obsolete
    ::= { snmp  22 }

snmpOutGenErrs OBJECT-TYPE
    SYNTAX     Counter32
    MAX-ACCESS read-only
    STATUS     obsolete
    ::= { snmp  24 }

snmpOutGetRequests OBJECT-TYPE
    SYNTAX     Counter32
    MAX-ACCESS read-only
    STATUS     obsolete
    ::= { snmp  25 }

snmpOutGetNexts OBJECT-TYPE
    SYNTAX     Counter32
    MAX-ACCESS read-only
    STATUS     obsolete
    ::= { snmp  26 }

snmpOutSetRequests OBJECT-TYPE
    SYNTAX     Counter32
    MAX-ACCESS read-only
    STATUS     obsolete
    ::= { snmp  27 }

snmpOutGetResponses OBJECT-TYPE
    SYNTAX     Counter32
    MAX-ACCESS read-only
    STATUS     obsolete
    ::= { snmp  28 }

snmpOutTraps OBJECT-TYPE
    SYNTAX     Counter32
    MAX-ACCESS read-only
    STATUS     obsolete
    ::= { snmp  29 }

snmpObsoleteGroup OBJECT-GROUP
    OBJECTS    {
                 snmpOutPkts,
                 snmpInTooBigs,
                 snmpInNoSuchNames,
                 snmpInBadValues,
                 snmpInReadOnlys,
                 snmpInGenErrs,
                 snmpInTotalReqVars,
                 snmpInTotalSetVars,
                 snmpInGetRequests,
                 snmpInGetNexts,
                 snmpInSetRequests,
                 snmpInGetResponses,
                 snmpInTraps,
                 snmpOutTooBigs,
                 snmpOutNoSuchNames,
                 snmpOutBadValues,
                 snmpOutGenErrs,
                 snmpOutGetRequests,
                 snmpOutGetNexts,
                 snmpOutSetRequests,
                 snmpOutGetResponses,
                 snmpOutTraps
               }
    STATUS     obsolete
    ::= { snmpMIBGroups  10 }

END
