IP-MIB DEFINITIONS ::= BEGIN

IMPORTS
    OBJECT-GROUP, MODULE-COMPLIANCE
        FROM SNMPv2-CONF
    PhysAddress
        FROM SNMPv2-TC
    mib-2, IpAddress, Counter32, Integer32, OBJECT-TYPE, MODULE-IDENTITY
        FROM SNMPv2-SMI;

ipMIB MODULE-IDENTITY
    LAST-UPDATED "9411010000Z"
    ORGANIZATION "IETF SNMPv2 Working Group"
    CONTACT-INFO
                 "Keith McCloghrie

          Postal: Cisco Systems, Inc.
                  170 West Tasman Drive
                  San Jose, CA  95134-1706
                  US

          Phone:  +1 408 526 5260
          Email:  kzm@cisco.com"
    REVISION     "9103310000Z"
    ::= { mib-2  48 }

ip ::= { mib-2  4 }

ipForwarding OBJECT-TYPE
    SYNTAX     INTEGER {
                 forwarding(1),
                 notForwarding(2)
               }
    MAX-ACCESS read-write
    STATUS     current
    ::= { ip  1 }

ipDefaultTTL OBJECT-TYPE
    SYNTAX     INTEGER
    MAX-ACCESS read-write
    STATUS     current
    ::= { ip  2 }

ipInReceives OBJECT-TYPE
    SYNTAX     Counter32
    MAX-ACCESS read-only
    STATUS     current
    ::= { ip  3 }

ipInHdrErrors OBJECT-TYPE
    SYNTAX     Counter32
    MAX-ACCESS read-only
    STATUS     current
    ::= { ip  4 }

ipInAddrErrors OBJECT-TYPE
    SYNTAX     Counter32
    MAX-ACCESS read-only
    STATUS     current
    ::= { ip  5 }

ipForwDatagrams OBJECT-TYPE
    SYNTAX     Counter32
    MAX-ACCESS read-only
    STATUS     current
    ::= { ip  6 }

ipInUnknownProtos OBJECT-TYPE
    SYNTAX     Counter32
    MAX-ACCESS read-only
    STATUS     current
    ::= { ip  7 }

ipInDiscards OBJECT-TYPE
    SYNTAX     Counter32
    MAX-ACCESS read-only
    STATUS     current
    ::= { ip  8 }

ipInDelivers OBJECT-TYPE
    SYNTAX     Counter32
    MAX-ACCESS read-only
    STATUS     current
    ::= { ip  9 }

ipOutRequests OBJECT-TYPE
    SYNTAX     Counter32
    MAX-ACCESS read-only
    STATUS     current
    ::= { ip  10 }

ipOutDiscards OBJECT-TYPE
    SYNTAX     Counter32
    MAX-ACCESS read-only
    STATUS     current
    ::= { ip  11 }

ipOutNoRoutes OBJECT-TYPE
    SYNTAX     Counter32
    MAX-ACCESS read-only
    STATUS     current
    ::= { ip  12 }

ipReasmTimeout OBJECT-TYPE
    SYNTAX     Integer32
    MAX-ACCESS read-only
    STATUS     current
    ::= { ip  13 }

ipReasmReqds OBJECT-TYPE
    SYNTAX     Counter32
    MAX-ACCESS read-only
    STATUS     current
    ::= { ip  14 }

ipReasmOKs OBJECT-TYPE
    SYNTAX     Counter32
    MAX-ACCESS read-only
    STATUS     current
    ::= { ip  15 }

ipReasmFails OBJECT-TYPE
    SYNTAX     Counter32
    MAX-ACCESS read-only
    STATUS     current
    ::= { ip  16 }

ipFragOKs OBJECT-TYPE
    SYNTAX     Counter32
    MAX-ACCESS read-only
    STATUS     current
    ::= { ip  17 }

ipFragFails OBJECT-TYPE
    SYNTAX     Counter32
    MAX-ACCESS read-only
    STATUS     current
    ::= { ip  18 }

ipFragCreates OBJECT-TYPE
    SYNTAX     Counter32
    MAX-ACCESS read-only
    STATUS     current
    ::= { ip  19 }

ipAddrTable OBJECT-TYPE
    SYNTAX     SEQUENCE OF IpAddrEntry
    MAX-ACCESS not-accessible
    STATUS     current
    ::= { ip  20 }

ipAddrEntry OBJECT-TYPE
    SYNTAX     IpAddrEntry
    MAX-ACCESS not-accessible
    STATUS     current
    INDEX      { ipAdEntAddr }
    ::= { ipAddrTable  1 }

IpAddrEntry ::=
    SEQUENCE {
        ipAdEntAddr
            IpAddress,

        ipAdEntIfIndex
            INTEGER,

        ipAdEntNetMask
            IpAddress,

        ipAdEntBcastAddr
            INTEGER,

        ipAdEntReasmMaxSize
            INTEGER
    }

ipAdEntAddr OBJECT-TYPE
    SYNTAX     IpAddress
    MAX-ACCESS read-only
    STATUS     current
    ::= { ipAddrEntry  1 }

ipAdEntIfIndex OBJECT-TYPE
    SYNTAX     INTEGER
    MAX-ACCESS read-only
    STATUS     current
    ::= { ipAddrEntry  2 }

ipAdEntNetMask OBJECT-TYPE
    SYNTAX     IpAddress
    MAX-ACCESS read-only
    STATUS     current
    ::= { ipAddrEntry  3 }

ipAdEntBcastAddr OBJECT-TYPE
    SYNTAX     INTEGER
    MAX-ACCESS read-only
    STATUS     current
    ::= { ipAddrEntry  4 }

ipAdEntReasmMaxSize OBJECT-TYPE
    SYNTAX     INTEGER
    MAX-ACCESS read-only
    STATUS     current
    ::= { ipAddrEntry  5 }

ipNetToMediaTable OBJECT-TYPE
    SYNTAX     SEQUENCE OF IpNetToMediaEntry
    MAX-ACCESS not-accessible
    STATUS     current
    ::= { ip  22 }

ipNetToMediaEntry OBJECT-TYPE
    SYNTAX     IpNetToMediaEntry
    MAX-ACCESS not-accessible
    STATUS     current
    INDEX      { ipNetToMediaIfIndex,  ipNetToMediaNetAddress }
    ::= { ipNetToMediaTable  1 }

IpNetToMediaEntry ::=
    SEQUENCE {
        ipNetToMediaIfIndex
            INTEGER,

        ipNetToMediaPhysAddress
            PhysAddress,

        ipNetToMediaNetAddress
            IpAddress,

        ipNetToMediaType
            INTEGER
    }

ipNetToMediaIfIndex OBJECT-TYPE
    SYNTAX     INTEGER
    MAX-ACCESS read-create
    STATUS     current
    ::= { ipNetToMediaEntry  1 }

ipNetToMediaPhysAddress OBJECT-TYPE
    SYNTAX     PhysAddress
    MAX-ACCESS read-create
    STATUS     current
    ::= { ipNetToMediaEntry  2 }

ipNetToMediaNetAddress OBJECT-TYPE
    SYNTAX     IpAddress
    MAX-ACCESS read-create
    STATUS     current
    ::= { ipNetToMediaEntry  3 }

ipNetToMediaType OBJECT-TYPE
    SYNTAX     INTEGER {
                 other(1),
                 invalid(2),
                 dynamic(3),
                 static(4)
               }
    MAX-ACCESS read-create
    STATUS     current
    ::= { ipNetToMediaEntry  4 }

ipRoutingDiscards OBJECT-TYPE
    SYNTAX     Counter32
    MAX-ACCESS read-only
    STATUS     current
    ::= { ip  23 }

icmp ::= { mib-2  5 }

icmpInMsgs OBJECT-TYPE
    SYNTAX     Counter32
    MAX-ACCESS read-only
    STATUS     current
    ::= { icmp  1 }

icmpInErrors OBJECT-TYPE
    SYNTAX     Counter32
    MAX-ACCESS read-only
    STATUS     current
    ::= { icmp  2 }

icmpInDestUnreachs OBJECT-TYPE
    SYNTAX     Counter32
    MAX-ACCESS read-only
    STATUS     current
    ::= { icmp  3 }

icmpInTimeExcds OBJECT-TYPE
    SYNTAX     Counter32
    MAX-ACCESS read-only
    STATUS     current
    ::= { icmp  4 }

icmpInParmProbs OBJECT-TYPE
    SYNTAX     Counter32
    MAX-ACCESS read-only
    STATUS     current
    ::= { icmp  5 }

icmpInSrcQuenchs OBJECT-TYPE
    SYNTAX     Counter32
    MAX-ACCESS read-only
    STATUS     current
    ::= { icmp  6 }

icmpInRedirects OBJECT-TYPE
    SYNTAX     Counter32
    MAX-ACCESS read-only
    STATUS     current
    ::= { icmp  7 }

icmpInEchos OBJECT-TYPE
    SYNTAX     Counter32
    MAX-ACCESS read-only
    STATUS     current
    ::= { icmp  8 }

icmpInEchoReps OBJECT-TYPE
    SYNTAX     Counter32
    MAX-ACCESS read-only
    STATUS     current
    ::= { icmp  9 }

icmpInTimestamps OBJECT-TYPE
    SYNTAX     Counter32
    MAX-ACCESS read-only
    STATUS     current
    ::= { icmp  10 }

icmpInTimestampReps OBJECT-TYPE
    SYNTAX     Counter32
    MAX-ACCESS read-only
    STATUS     current
    ::= { icmp  11 }

icmpInAddrMasks OBJECT-TYPE
    SYNTAX     Counter32
    MAX-ACCESS read-only
    STATUS     current
    ::= { icmp  12 }

icmpInAddrMaskReps OBJECT-TYPE
    SYNTAX     Counter32
    MAX-ACCESS read-only
    STATUS     current
    ::= { icmp  13 }

icmpOutMsgs OBJECT-TYPE
    SYNTAX     Counter32
    MAX-ACCESS read-only
    STATUS     current
    ::= { icmp  14 }

icmpOutErrors OBJECT-TYPE
    SYNTAX     Counter32
    MAX-ACCESS read-only
    STATUS     current
    ::= { icmp  15 }

icmpOutDestUnreachs OBJECT-TYPE
    SYNTAX     Counter32
    MAX-ACCESS read-only
    STATUS     current
    ::= { icmp  16 }

icmpOutTimeExcds OBJECT-TYPE
    SYNTAX     Counter32
    MAX-ACCESS read-only
    STATUS     current
    ::= { icmp  17 }

icmpOutParmProbs OBJECT-TYPE
    SYNTAX     Counter32
    MAX-ACCESS read-only
    STATUS     current
    ::= { icmp  18 }

icmpOutSrcQuenchs OBJECT-TYPE
    SYNTAX     Counter32
    MAX-ACCESS read-only
    STATUS     current
    ::= { icmp  19 }

icmpOutRedirects OBJECT-TYPE
    SYNTAX     Counter32
    MAX-ACCESS read-only
    STATUS     current
    ::= { icmp  20 }

icmpOutEchos OBJECT-TYPE
    SYNTAX     Counter32
    MAX-ACCESS read-only
    STATUS     current
    ::= { icmp  21 }

icmpOutEchoReps OBJECT-TYPE
    SYNTAX     Counter32
    MAX-ACCESS read-only
    STATUS     current
    ::= { icmp  22 }

icmpOutTimestamps OBJECT-TYPE
    SYNTAX     Counter32
    MAX-ACCESS read-only
    STATUS     current
    ::= { icmp  23 }

icmpOutTimestampReps OBJECT-TYPE
    SYNTAX     Counter32
    MAX-ACCESS read-only
    STATUS     current
    ::= { icmp  24 }

icmpOutAddrMasks OBJECT-TYPE
    SYNTAX     Counter32
    MAX-ACCESS read-only
    STATUS     current
    ::= { icmp  25 }

icmpOutAddrMaskReps OBJECT-TYPE
    SYNTAX     Counter32
    MAX-ACCESS read-only
    STATUS     current
    ::= { icmp  26 }

ipMIBConformance ::= { ipMIB  2 }

ipMIBCompliances ::= { ipMIBConformance  1 }

ipMIBGroups ::= { ipMIBConformance  2 }

ipMIBCompliance MODULE-COMPLIANCE
    STATUS     current

    MANDATORY-GROUPS { ipGroup,  icmpGroup }
    ::= { ipMIBCompliances  1 }

ipGroup OBJECT-GROUP
    OBJECTS    {
                 ipForwarding,
                 ipDefaultTTL,
                 ipInReceives,
                 ipInHdrErrors,
                 ipInAddrErrors,
                 ipForwDatagrams,
                 ipInUnknownProtos,
                 ipInDiscards,
                 ipInDelivers,
                 ipOutRequests,
                 ipOutDiscards,
                 ipOutNoRoutes,
                 ipReasmTimeout,
                 ipReasmReqds,
                 ipReasmOKs,
                 ipReasmFails,
                 ipFragOKs,
                 ipFragFails,
                 ipFragCreates,
                 ipAdEntAddr,
                 ipAdEntIfIndex,
                 ipAdEntNetMask,
                 ipAdEntBcastAddr,
                 ipAdEntReasmMaxSize,
                 ipNetToMediaIfIndex,
                 ipNetToMediaPhysAddress,
                 ipNetToMediaNetAddress,
                 ipNetToMediaType,
                 ipRoutingDiscards
               }
    STATUS     current
    ::= { ipMIBGroups  1 }

icmpGroup OBJECT-GROUP
    OBJECTS    {
                 icmpInMsgs,
                 icmpInErrors,
                 icmpInDestUnreachs,
                 icmpInTimeExcds,
                 icmpInParmProbs,
                 icmpInSrcQuenchs,
                 icmpInRedirects,
                 icmpInEchos,
                 icmpInEchoReps,
                 icmpInTimestamps,
                 icmpInTimestampReps,
                 icmpInAddrMasks,
                 icmpInAddrMaskReps,
                 icmpOutMsgs,
                 icmpOutErrors,
                 icmpOutDestUnreachs,
                 icmpOutTimeExcds,
                 icmpOutParmProbs,
                 icmpOutSrcQuenchs,
                 icmpOutRedirects,
                 icmpOutEchos,
                 icmpOutEchoReps,
                 icmpOutTimestamps,
                 icmpOutTimestampReps,
                 icmpOutAddrMasks,
                 icmpOutAddrMaskReps
               }
    STATUS     current
    ::= { ipMIBGroups  2 }

END
