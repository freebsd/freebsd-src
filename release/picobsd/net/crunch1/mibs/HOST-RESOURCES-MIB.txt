HOST-RESOURCES-MIB DEFINITIONS ::= BEGIN

IMPORTS
    Gauge, Counter, TimeTicks
        FROM RFC1155-SMI
    mib-2, DisplayString
        FROM RFC1213-MIB
    OBJECT-TYPE
        FROM RFC-1212;

host ::= { mib-2  25 }

hrSystem ::= { host  1 }

hrStorage ::= { host  2 }

hrDevice ::= { host  3 }

hrSWRun ::= { host  4 }

hrSWRunPerf ::= { host  5 }

hrSWInstalled ::= { host  6 }

Boolean ::=
    INTEGER {
 true(1),
 false(2)
 }

KBytes ::=
    INTEGER

ProductID ::=
    OBJECT IDENTIFIER

DateAndTime ::=
    OCTET STRING

InternationalDisplayString ::=
    OCTET STRING

hrSystemUptime OBJECT-TYPE
    SYNTAX     TimeTicks
    ACCESS     read-only
    STATUS     mandatory
    ::= { hrSystem  1 }

hrSystemDate OBJECT-TYPE
    SYNTAX     DateAndTime
    ACCESS     read-write
    STATUS     mandatory
    ::= { hrSystem  2 }

hrSystemInitialLoadDevice OBJECT-TYPE
    SYNTAX     INTEGER
    ACCESS     read-write
    STATUS     mandatory
    ::= { hrSystem  3 }

hrSystemInitialLoadParameters OBJECT-TYPE
    SYNTAX     InternationalDisplayString
    ACCESS     read-write
    STATUS     mandatory
    ::= { hrSystem  4 }

hrSystemNumUsers OBJECT-TYPE
    SYNTAX     Gauge
    ACCESS     read-only
    STATUS     mandatory
    ::= { hrSystem  5 }

hrSystemProcesses OBJECT-TYPE
    SYNTAX     Gauge
    ACCESS     read-only
    STATUS     mandatory
    ::= { hrSystem  6 }

hrSystemMaxProcesses OBJECT-TYPE
    SYNTAX     INTEGER
    ACCESS     read-only
    STATUS     mandatory
    ::= { hrSystem  7 }

hrStorageTypes ::= { hrStorage  1 }

hrStorageOther ::= { hrStorageTypes  1 }

hrStorageRam ::= { hrStorageTypes  2 }

hrStorageVirtualMemory ::= { hrStorageTypes  3 }

hrStorageFixedDisk ::= { hrStorageTypes  4 }

hrStorageRemovableDisk ::= { hrStorageTypes  5 }

hrStorageFloppyDisk ::= { hrStorageTypes  6 }

hrStorageCompactDisc ::= { hrStorageTypes  7 }

hrStorageRamDisk ::= { hrStorageTypes  8 }

hrMemorySize OBJECT-TYPE
    SYNTAX     KBytes
    ACCESS     read-only
    STATUS     mandatory
    ::= { hrStorage  2 }

hrStorageTable OBJECT-TYPE
    SYNTAX     SEQUENCE OF HrStorageEntry
    ACCESS     not-accessible
    STATUS     mandatory
    ::= { hrStorage  3 }

hrStorageEntry OBJECT-TYPE
    SYNTAX     HrStorageEntry
    ACCESS     not-accessible
    STATUS     mandatory
    INDEX      { hrStorageIndex }
    ::= { hrStorageTable  1 }

HrStorageEntry ::=
    SEQUENCE {
        hrStorageIndex
            INTEGER,

        hrStorageType
            OBJECT IDENTIFIER,

        hrStorageDescr
            DisplayString,

        hrStorageAllocationUnits
            INTEGER,

        hrStorageSize
            INTEGER,

        hrStorageUsed
            INTEGER,

        hrStorageAllocationFailures
            Counter
    }

hrStorageIndex OBJECT-TYPE
    SYNTAX     INTEGER
    ACCESS     read-only
    STATUS     mandatory
    ::= { hrStorageEntry  1 }

hrStorageType OBJECT-TYPE
    SYNTAX     OBJECT IDENTIFIER
    ACCESS     read-only
    STATUS     mandatory
    ::= { hrStorageEntry  2 }

hrStorageDescr OBJECT-TYPE
    SYNTAX     DisplayString
    ACCESS     read-only
    STATUS     mandatory
    ::= { hrStorageEntry  3 }

hrStorageAllocationUnits OBJECT-TYPE
    SYNTAX     INTEGER
    ACCESS     read-only
    STATUS     mandatory
    ::= { hrStorageEntry  4 }

hrStorageSize OBJECT-TYPE
    SYNTAX     INTEGER
    ACCESS     read-write
    STATUS     mandatory
    ::= { hrStorageEntry  5 }

hrStorageUsed OBJECT-TYPE
    SYNTAX     INTEGER
    ACCESS     read-only
    STATUS     mandatory
    ::= { hrStorageEntry  6 }

hrStorageAllocationFailures OBJECT-TYPE
    SYNTAX     Counter
    ACCESS     read-only
    STATUS     mandatory
    ::= { hrStorageEntry  7 }

hrDeviceTypes ::= { hrDevice  1 }

hrDeviceOther ::= { hrDeviceTypes  1 }

hrDeviceUnknown ::= { hrDeviceTypes  2 }

hrDeviceProcessor ::= { hrDeviceTypes  3 }

hrDeviceNetwork ::= { hrDeviceTypes  4 }

hrDevicePrinter ::= { hrDeviceTypes  5 }

hrDeviceDiskStorage ::= { hrDeviceTypes  6 }

hrDeviceVideo ::= { hrDeviceTypes  10 }

hrDeviceAudio ::= { hrDeviceTypes  11 }

hrDeviceCoprocessor ::= { hrDeviceTypes  12 }

hrDeviceKeyboard ::= { hrDeviceTypes  13 }

hrDeviceModem ::= { hrDeviceTypes  14 }

hrDeviceParallelPort ::= { hrDeviceTypes  15 }

hrDevicePointing ::= { hrDeviceTypes  16 }

hrDeviceSerialPort ::= { hrDeviceTypes  17 }

hrDeviceTape ::= { hrDeviceTypes  18 }

hrDeviceClock ::= { hrDeviceTypes  19 }

hrDeviceVolatileMemory ::= { hrDeviceTypes  20 }

hrDeviceNonVolatileMemory ::= { hrDeviceTypes  21 }

hrDeviceTable OBJECT-TYPE
    SYNTAX     SEQUENCE OF HrDeviceEntry
    ACCESS     not-accessible
    STATUS     mandatory
    ::= { hrDevice  2 }

hrDeviceEntry OBJECT-TYPE
    SYNTAX     HrDeviceEntry
    ACCESS     not-accessible
    STATUS     mandatory
    INDEX      { hrDeviceIndex }
    ::= { hrDeviceTable  1 }

HrDeviceEntry ::=
    SEQUENCE {
        hrDeviceIndex
            INTEGER,

        hrDeviceType
            OBJECT IDENTIFIER,

        hrDeviceDescr
            DisplayString,

        hrDeviceID
            ProductID,

        hrDeviceStatus
            INTEGER,

        hrDeviceErrors
            Counter
    }

hrDeviceIndex OBJECT-TYPE
    SYNTAX     INTEGER
    ACCESS     read-only
    STATUS     mandatory
    ::= { hrDeviceEntry  1 }

hrDeviceType OBJECT-TYPE
    SYNTAX     OBJECT IDENTIFIER
    ACCESS     read-only
    STATUS     mandatory
    ::= { hrDeviceEntry  2 }

hrDeviceDescr OBJECT-TYPE
    SYNTAX     DisplayString
    ACCESS     read-only
    STATUS     mandatory
    ::= { hrDeviceEntry  3 }

hrDeviceID OBJECT-TYPE
    SYNTAX     ProductID
    ACCESS     read-only
    STATUS     mandatory
    ::= { hrDeviceEntry  4 }

hrDeviceStatus OBJECT-TYPE
    SYNTAX     INTEGER {
                 unknown(1),
                 running(2),
                 warning(3),
                 testing(4),
                 down(5)
               }
    ACCESS     read-only
    STATUS     mandatory
    ::= { hrDeviceEntry  5 }

hrDeviceErrors OBJECT-TYPE
    SYNTAX     Counter
    ACCESS     read-only
    STATUS     mandatory
    ::= { hrDeviceEntry  6 }

hrProcessorTable OBJECT-TYPE
    SYNTAX     SEQUENCE OF HrProcessorEntry
    ACCESS     not-accessible
    STATUS     mandatory
    ::= { hrDevice  3 }

hrProcessorEntry OBJECT-TYPE
    SYNTAX     HrProcessorEntry
    ACCESS     not-accessible
    STATUS     mandatory
    INDEX      { hrDeviceIndex }
    ::= { hrProcessorTable  1 }

HrProcessorEntry ::=
    SEQUENCE {
        hrProcessorFrwID
            ProductID,

        hrProcessorLoad
            INTEGER
    }

hrProcessorFrwID OBJECT-TYPE
    SYNTAX     ProductID
    ACCESS     read-only
    STATUS     mandatory
    ::= { hrProcessorEntry  1 }

hrProcessorLoad OBJECT-TYPE
    SYNTAX     INTEGER
    ACCESS     read-only
    STATUS     mandatory
    ::= { hrProcessorEntry  2 }

hrNetworkTable OBJECT-TYPE
    SYNTAX     SEQUENCE OF HrNetworkEntry
    ACCESS     not-accessible
    STATUS     mandatory
    ::= { hrDevice  4 }

hrNetworkEntry OBJECT-TYPE
    SYNTAX     HrNetworkEntry
    ACCESS     not-accessible
    STATUS     mandatory
    INDEX      { hrDeviceIndex }
    ::= { hrNetworkTable  1 }

HrNetworkEntry ::=
    SEQUENCE {
        hrNetworkIfIndex
            INTEGER
    }

hrNetworkIfIndex OBJECT-TYPE
    SYNTAX     INTEGER
    ACCESS     read-only
    STATUS     mandatory
    ::= { hrNetworkEntry  1 }

hrPrinterTable OBJECT-TYPE
    SYNTAX     SEQUENCE OF HrPrinterEntry
    ACCESS     not-accessible
    STATUS     mandatory
    ::= { hrDevice  5 }

hrPrinterEntry OBJECT-TYPE
    SYNTAX     HrPrinterEntry
    ACCESS     not-accessible
    STATUS     mandatory
    INDEX      { hrDeviceIndex }
    ::= { hrPrinterTable  1 }

HrPrinterEntry ::=
    SEQUENCE {
        hrPrinterStatus
            INTEGER,

        hrPrinterDetectedErrorState
            OCTET STRING
    }

hrPrinterStatus OBJECT-TYPE
    SYNTAX     INTEGER {
                 other(1),
                 unknown(2),
                 idle(3),
                 printing(4),
                 warmup(5)
               }
    ACCESS     read-only
    STATUS     mandatory
    ::= { hrPrinterEntry  1 }

hrPrinterDetectedErrorState OBJECT-TYPE
    SYNTAX     OCTET STRING
    ACCESS     read-only
    STATUS     mandatory
    ::= { hrPrinterEntry  2 }

hrDiskStorageTable OBJECT-TYPE
    SYNTAX     SEQUENCE OF HrDiskStorageEntry
    ACCESS     not-accessible
    STATUS     mandatory
    ::= { hrDevice  6 }

hrDiskStorageEntry OBJECT-TYPE
    SYNTAX     HrDiskStorageEntry
    ACCESS     not-accessible
    STATUS     mandatory
    INDEX      { hrDeviceIndex }
    ::= { hrDiskStorageTable  1 }

HrDiskStorageEntry ::=
    SEQUENCE {
        hrDiskStorageAccess
            INTEGER,

        hrDiskStorageMedia
            INTEGER,

        hrDiskStorageRemoveble
            Boolean,

        hrDiskStorageCapacity
            KBytes
    }

hrDiskStorageAccess OBJECT-TYPE
    SYNTAX     INTEGER {
                 readWrite(1),
                 readOnly(2)
               }
    ACCESS     read-only
    STATUS     mandatory
    ::= { hrDiskStorageEntry  1 }

hrDiskStorageMedia OBJECT-TYPE
    SYNTAX     INTEGER {
                 other(1),
                 unknown(2),
                 hardDisk(3),
                 floppyDisk(4),
                 opticalDiskROM(5),
                 opticalDiskWORM(6),
                 opticalDiskRW(7),
                 ramDisk(8)
               }
    ACCESS     read-only
    STATUS     mandatory
    ::= { hrDiskStorageEntry  2 }

hrDiskStorageRemoveble OBJECT-TYPE
    SYNTAX     Boolean
    ACCESS     read-only
    STATUS     mandatory
    ::= { hrDiskStorageEntry  3 }

hrDiskStorageCapacity OBJECT-TYPE
    SYNTAX     KBytes
    ACCESS     read-only
    STATUS     mandatory
    ::= { hrDiskStorageEntry  4 }

hrPartitionTable OBJECT-TYPE
    SYNTAX     SEQUENCE OF HrPartitionEntry
    ACCESS     not-accessible
    STATUS     mandatory
    ::= { hrDevice  7 }

hrPartitionEntry OBJECT-TYPE
    SYNTAX     HrPartitionEntry
    ACCESS     not-accessible
    STATUS     mandatory
    INDEX      { hrDeviceIndex,  hrPartitionIndex }
    ::= { hrPartitionTable  1 }

HrPartitionEntry ::=
    SEQUENCE {
        hrPartitionIndex
            INTEGER,

        hrPartitionLabel
            InternationalDisplayString,

        hrPartitionID
            OCTET STRING,

        hrPartitionSize
            KBytes,

        hrPartitionFSIndex
            INTEGER
    }

hrPartitionIndex OBJECT-TYPE
    SYNTAX     INTEGER
    ACCESS     read-only
    STATUS     mandatory
    ::= { hrPartitionEntry  1 }

hrPartitionLabel OBJECT-TYPE
    SYNTAX     InternationalDisplayString
    ACCESS     read-only
    STATUS     mandatory
    ::= { hrPartitionEntry  2 }

hrPartitionID OBJECT-TYPE
    SYNTAX     OCTET STRING
    ACCESS     read-only
    STATUS     mandatory
    ::= { hrPartitionEntry  3 }

hrPartitionSize OBJECT-TYPE
    SYNTAX     KBytes
    ACCESS     read-only
    STATUS     mandatory
    ::= { hrPartitionEntry  4 }

hrPartitionFSIndex OBJECT-TYPE
    SYNTAX     INTEGER
    ACCESS     read-only
    STATUS     mandatory
    ::= { hrPartitionEntry  5 }

hrFSTable OBJECT-TYPE
    SYNTAX     SEQUENCE OF HrFSEntry
    ACCESS     not-accessible
    STATUS     mandatory
    ::= { hrDevice  8 }

hrFSEntry OBJECT-TYPE
    SYNTAX     HrFSEntry
    ACCESS     not-accessible
    STATUS     mandatory
    INDEX      { hrFSIndex }
    ::= { hrFSTable  1 }

hrFSTypes ::= { hrDevice  9 }

hrFSOther ::= { hrFSTypes  1 }

hrFSUnknown ::= { hrFSTypes  2 }

hrFSBerkeleyFFS ::= { hrFSTypes  3 }

hrFSSys5FS ::= { hrFSTypes  4 }

hrFSFat ::= { hrFSTypes  5 }

hrFSHPFS ::= { hrFSTypes  6 }

hrFSHFS ::= { hrFSTypes  7 }

hrFSMFS ::= { hrFSTypes  8 }

hrFSNTFS ::= { hrFSTypes  9 }

hrFSVNode ::= { hrFSTypes  10 }

hrFSJournaled ::= { hrFSTypes  11 }

hrFSiso9660 ::= { hrFSTypes  12 }

hrFSRockRidge ::= { hrFSTypes  13 }

hrFSNFS ::= { hrFSTypes  14 }

hrFSNetware ::= { hrFSTypes  15 }

hrFSAFS ::= { hrFSTypes  16 }

hrFSDFS ::= { hrFSTypes  17 }

hrFSAppleshare ::= { hrFSTypes  18 }

hrFSRFS ::= { hrFSTypes  19 }

hrFSDGCFS ::= { hrFSTypes  20 }

hrFSBFS ::= { hrFSTypes  21 }

HrFSEntry ::=
    SEQUENCE {
        hrFSIndex
            INTEGER,

        hrFSMountPoint
            InternationalDisplayString,

        hrFSRemoteMountPoint
            InternationalDisplayString,

        hrFSType
            OBJECT IDENTIFIER,

        hrFSAccess
            INTEGER,

        hrFSBootable
            Boolean,

        hrFSStorageIndex
            INTEGER,

        hrFSLastFullBackupDate
            DateAndTime,

        hrFSLastPartialBackupDate
            DateAndTime
    }

hrFSIndex OBJECT-TYPE
    SYNTAX     INTEGER
    ACCESS     read-only
    STATUS     mandatory
    ::= { hrFSEntry  1 }

hrFSMountPoint OBJECT-TYPE
    SYNTAX     InternationalDisplayString
    ACCESS     read-only
    STATUS     mandatory
    ::= { hrFSEntry  2 }

hrFSRemoteMountPoint OBJECT-TYPE
    SYNTAX     InternationalDisplayString
    ACCESS     read-only
    STATUS     mandatory
    ::= { hrFSEntry  3 }

hrFSType OBJECT-TYPE
    SYNTAX     OBJECT IDENTIFIER
    ACCESS     read-only
    STATUS     mandatory
    ::= { hrFSEntry  4 }

hrFSAccess OBJECT-TYPE
    SYNTAX     INTEGER {
                 readWrite(1),
                 readOnly(2)
               }
    ACCESS     read-only
    STATUS     mandatory
    ::= { hrFSEntry  5 }

hrFSBootable OBJECT-TYPE
    SYNTAX     Boolean
    ACCESS     read-only
    STATUS     mandatory
    ::= { hrFSEntry  6 }

hrFSStorageIndex OBJECT-TYPE
    SYNTAX     INTEGER
    ACCESS     read-only
    STATUS     mandatory
    ::= { hrFSEntry  7 }

hrFSLastFullBackupDate OBJECT-TYPE
    SYNTAX     DateAndTime
    ACCESS     read-write
    STATUS     mandatory
    ::= { hrFSEntry  8 }

hrFSLastPartialBackupDate OBJECT-TYPE
    SYNTAX     DateAndTime
    ACCESS     read-write
    STATUS     mandatory
    ::= { hrFSEntry  9 }

hrSWOSIndex OBJECT-TYPE
    SYNTAX     INTEGER
    ACCESS     read-only
    STATUS     mandatory
    ::= { hrSWRun  1 }

hrSWRunTable OBJECT-TYPE
    SYNTAX     SEQUENCE OF HrSWRunEntry
    ACCESS     not-accessible
    STATUS     mandatory
    ::= { hrSWRun  2 }

hrSWRunEntry OBJECT-TYPE
    SYNTAX     HrSWRunEntry
    ACCESS     not-accessible
    STATUS     mandatory
    INDEX      { hrSWRunIndex }
    ::= { hrSWRunTable  1 }

HrSWRunEntry ::=
    SEQUENCE {
        hrSWRunIndex
            INTEGER,

        hrSWRunName
            InternationalDisplayString,

        hrSWRunID
            ProductID,

        hrSWRunPath
            InternationalDisplayString,

        hrSWRunParameters
            InternationalDisplayString,

        hrSWRunType
            INTEGER,

        hrSWRunStatus
            INTEGER
    }

hrSWRunIndex OBJECT-TYPE
    SYNTAX     INTEGER
    ACCESS     read-only
    STATUS     mandatory
    ::= { hrSWRunEntry  1 }

hrSWRunName OBJECT-TYPE
    SYNTAX     InternationalDisplayString
    ACCESS     read-only
    STATUS     mandatory
    ::= { hrSWRunEntry  2 }

hrSWRunID OBJECT-TYPE
    SYNTAX     ProductID
    ACCESS     read-only
    STATUS     mandatory
    ::= { hrSWRunEntry  3 }

hrSWRunPath OBJECT-TYPE
    SYNTAX     InternationalDisplayString
    ACCESS     read-only
    STATUS     mandatory
    ::= { hrSWRunEntry  4 }

hrSWRunParameters OBJECT-TYPE
    SYNTAX     InternationalDisplayString
    ACCESS     read-only
    STATUS     mandatory
    ::= { hrSWRunEntry  5 }

hrSWRunType OBJECT-TYPE
    SYNTAX     INTEGER {
                 unknown(1),
                 operatingSystem(2),
                 deviceDriver(3),
                 application(4)
               }
    ACCESS     read-only
    STATUS     mandatory
    ::= { hrSWRunEntry  6 }

hrSWRunStatus OBJECT-TYPE
    SYNTAX     INTEGER {
                 running(1),
                 runnable(2),
                 notRunnable(3),
                 invalid(4)
               }
    ACCESS     read-write
    STATUS     mandatory
    ::= { hrSWRunEntry  7 }

hrSWRunPerfTable OBJECT-TYPE
    SYNTAX     SEQUENCE OF HrSWRunPerfEntry
    ACCESS     not-accessible
    STATUS     mandatory
    ::= { hrSWRunPerf  1 }

hrSWRunPerfEntry OBJECT-TYPE
    SYNTAX     HrSWRunPerfEntry
    ACCESS     not-accessible
    STATUS     mandatory
    INDEX      { hrSWRunIndex }
    ::= { hrSWRunPerfTable  1 }

HrSWRunPerfEntry ::=
    SEQUENCE {
        hrSWRunPerfCPU
            INTEGER,

        hrSWRunPerfMem
            KBytes
    }

hrSWRunPerfCPU OBJECT-TYPE
    SYNTAX     INTEGER
    ACCESS     read-only
    STATUS     mandatory
    ::= { hrSWRunPerfEntry  1 }

hrSWRunPerfMem OBJECT-TYPE
    SYNTAX     KBytes
    ACCESS     read-only
    STATUS     mandatory
    ::= { hrSWRunPerfEntry  2 }

hrSWInstalledLastChange OBJECT-TYPE
    SYNTAX     TimeTicks
    ACCESS     read-only
    STATUS     mandatory
    ::= { hrSWInstalled  1 }

hrSWInstalledLastUpdateTime OBJECT-TYPE
    SYNTAX     TimeTicks
    ACCESS     read-only
    STATUS     mandatory
    ::= { hrSWInstalled  2 }

hrSWInstalledTable OBJECT-TYPE
    SYNTAX     SEQUENCE OF HrSWInstalledEntry
    ACCESS     not-accessible
    STATUS     mandatory
    ::= { hrSWInstalled  3 }

hrSWInstalledEntry OBJECT-TYPE
    SYNTAX     HrSWInstalledEntry
    ACCESS     not-accessible
    STATUS     mandatory
    INDEX      { hrSWInstalledIndex }
    ::= { hrSWInstalledTable  1 }

HrSWInstalledEntry ::=
    SEQUENCE {
        hrSWInstalledIndex
            INTEGER,

        hrSWInstalledName
            InternationalDisplayString,

        hrSWInstalledID
            ProductID,

        hrSWInstalledType
            INTEGER,

        hrSWInstalledDate
            DateAndTime
    }

hrSWInstalledIndex OBJECT-TYPE
    SYNTAX     INTEGER
    ACCESS     read-only
    STATUS     mandatory
    ::= { hrSWInstalledEntry  1 }

hrSWInstalledName OBJECT-TYPE
    SYNTAX     InternationalDisplayString
    ACCESS     read-only
    STATUS     mandatory
    ::= { hrSWInstalledEntry  2 }

hrSWInstalledID OBJECT-TYPE
    SYNTAX     ProductID
    ACCESS     read-only
    STATUS     mandatory
    ::= { hrSWInstalledEntry  3 }

hrSWInstalledType OBJECT-TYPE
    SYNTAX     INTEGER {
                 unknown(1),
                 operatingSystem(2),
                 deviceDriver(3),
                 application(4)
               }
    ACCESS     read-only
    STATUS     mandatory
    ::= { hrSWInstalledEntry  4 }

hrSWInstalledDate OBJECT-TYPE
    SYNTAX     DateAndTime
    ACCESS     read-only
    STATUS     mandatory
    ::= { hrSWInstalledEntry  5 }

END
