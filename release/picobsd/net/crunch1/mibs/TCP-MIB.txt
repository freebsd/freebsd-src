TCP-MIB DEFINITIONS ::= BEGIN

IMPORTS
    OBJECT-GROUP, MODULE-COMPLIANCE
        FROM SNMPv2-CONF
    mib-2, IpAddress, Counter32, Gauge32, Integer32, OBJECT-TYPE, MODULE-IDENTITY
        FROM SNMPv2-SMI;

tcpMIB MODULE-IDENTITY
    LAST-UPDATED "9411010000Z"
    ORGANIZATION "IETF SNMPv2 Working Group"
    CONTACT-INFO
                 "Keith McCloghrie

          Postal: Cisco Systems, Inc.
                  170 West Tasman Drive
                  San Jose, CA  95134-1706
                  US

          Phone:  +1 408 526 5260
          Email:  kzm@cisco.com"
    REVISION     "9103310000Z"
    ::= { mib-2  49 }

tcp ::= { mib-2  6 }

tcpRtoAlgorithm OBJECT-TYPE
    SYNTAX     INTEGER {
                 other(1),
                 constant(2),
                 rsre(3),
                 vanj(4)
               }
    MAX-ACCESS read-only
    STATUS     current
    ::= { tcp  1 }

tcpRtoMin OBJECT-TYPE
    SYNTAX     Integer32
    UNITS      "milliseconds"
    MAX-ACCESS read-only
    STATUS     current
    ::= { tcp  2 }

tcpRtoMax OBJECT-TYPE
    SYNTAX     Integer32
    UNITS      "milliseconds"
    MAX-ACCESS read-only
    STATUS     current
    ::= { tcp  3 }

tcpMaxConn OBJECT-TYPE
    SYNTAX     Integer32
    MAX-ACCESS read-only
    STATUS     current
    ::= { tcp  4 }

tcpActiveOpens OBJECT-TYPE
    SYNTAX     Counter32
    MAX-ACCESS read-only
    STATUS     current
    ::= { tcp  5 }

tcpPassiveOpens OBJECT-TYPE
    SYNTAX     Counter32
    MAX-ACCESS read-only
    STATUS     current
    ::= { tcp  6 }

tcpAttemptFails OBJECT-TYPE
    SYNTAX     Counter32
    MAX-ACCESS read-only
    STATUS     current
    ::= { tcp  7 }

tcpEstabResets OBJECT-TYPE
    SYNTAX     Counter32
    MAX-ACCESS read-only
    STATUS     current
    ::= { tcp  8 }

tcpCurrEstab OBJECT-TYPE
    SYNTAX     Gauge32
    MAX-ACCESS read-only
    STATUS     current
    ::= { tcp  9 }

tcpInSegs OBJECT-TYPE
    SYNTAX     Counter32
    MAX-ACCESS read-only
    STATUS     current
    ::= { tcp  10 }

tcpOutSegs OBJECT-TYPE
    SYNTAX     Counter32
    MAX-ACCESS read-only
    STATUS     current
    ::= { tcp  11 }

tcpRetransSegs OBJECT-TYPE
    SYNTAX     Counter32
    MAX-ACCESS read-only
    STATUS     current
    ::= { tcp  12 }

tcpConnTable OBJECT-TYPE
    SYNTAX     SEQUENCE OF TcpConnEntry
    MAX-ACCESS not-accessible
    STATUS     current
    ::= { tcp  13 }

tcpConnEntry OBJECT-TYPE
    SYNTAX     TcpConnEntry
    MAX-ACCESS not-accessible
    STATUS     current
    INDEX      {
                 tcpConnLocalAddress,
                 tcpConnLocalPort,
                 tcpConnRemAddress,
                 tcpConnRemPort
               }
    ::= { tcpConnTable  1 }

TcpConnEntry ::=
    SEQUENCE {
        tcpConnState
            INTEGER,

        tcpConnLocalAddress
            IpAddress,

        tcpConnLocalPort
            INTEGER,

        tcpConnRemAddress
            IpAddress,

        tcpConnRemPort
            INTEGER
    }

tcpConnState OBJECT-TYPE
    SYNTAX     INTEGER {
                 closed(1),
                 listen(2),
                 synSent(3),
                 synReceived(4),
                 established(5),
                 finWait1(6),
                 finWait2(7),
                 closeWait(8),
                 lastAck(9),
                 closing(10),
                 timeWait(11),
                 deleteTCB(12)
               }
    MAX-ACCESS read-write
    STATUS     current
    ::= { tcpConnEntry  1 }

tcpConnLocalAddress OBJECT-TYPE
    SYNTAX     IpAddress
    MAX-ACCESS read-only
    STATUS     current
    ::= { tcpConnEntry  2 }

tcpConnLocalPort OBJECT-TYPE
    SYNTAX     INTEGER
    MAX-ACCESS read-only
    STATUS     current
    ::= { tcpConnEntry  3 }

tcpConnRemAddress OBJECT-TYPE
    SYNTAX     IpAddress
    MAX-ACCESS read-only
    STATUS     current
    ::= { tcpConnEntry  4 }

tcpConnRemPort OBJECT-TYPE
    SYNTAX     INTEGER
    MAX-ACCESS read-only
    STATUS     current
    ::= { tcpConnEntry  5 }

tcpInErrs OBJECT-TYPE
    SYNTAX     Counter32
    MAX-ACCESS read-only
    STATUS     current
    ::= { tcp  14 }

tcpOutRsts OBJECT-TYPE
    SYNTAX     Counter32
    MAX-ACCESS read-only
    STATUS     current
    ::= { tcp  15 }

tcpMIBConformance ::= { tcpMIB  2 }

tcpMIBCompliances ::= { tcpMIBConformance  1 }

tcpMIBGroups ::= { tcpMIBConformance  2 }

tcpMIBCompliance MODULE-COMPLIANCE
    STATUS     current

    MANDATORY-GROUPS { tcpGroup }
    ::= { tcpMIBCompliances  1 }

tcpGroup OBJECT-GROUP
    OBJECTS    {
                 tcpRtoAlgorithm,
                 tcpRtoMin,
                 tcpRtoMax,
                 tcpMaxConn,
                 tcpActiveOpens,
                 tcpPassiveOpens,
                 tcpAttemptFails,
                 tcpEstabResets,
                 tcpCurrEstab,
                 tcpInSegs,
                 tcpOutSegs,
                 tcpRetransSegs,
                 tcpConnState,
                 tcpConnLocalAddress,
                 tcpConnLocalPort,
                 tcpConnRemAddress,
                 tcpConnRemPort,
                 tcpInErrs,
                 tcpOutRsts
               }
    STATUS     current
    ::= { tcpMIBGroups  1 }

END
