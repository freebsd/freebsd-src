SNMPv2-TC DEFINITIONS ::= BEGIN

IMPORTS
        FROM SNMPv2-SMI;

DisplayString ::= TEXTUAL-CONVENTION
    DISPLAY-HINT "255a"
    STATUS       current
    SYNTAX       OCTET STRING

PhysAddress ::= TEXTUAL-CONVENTION
    DISPLAY-HINT "1x:"
    STATUS       current
    SYNTAX       OCTET STRING

MacAddress ::= TEXTUAL-CONVENTION
    DISPLAY-HINT "1x:"
    STATUS       current
    SYNTAX       OCTET STRING

TruthValue ::= TEXTUAL-CONVENTION
    STATUS       current
    SYNTAX       INTEGER {
                 true(1),
                 false(2)
               }

TestAndIncr ::= TEXTUAL-CONVENTION
    STATUS       current
    SYNTAX       INTEGER

AutonomousType ::= TEXTUAL-CONVENTION
    STATUS       current
    SYNTAX       OBJECT IDENTIFIER

InstancePointer ::= TEXTUAL-CONVENTION
    STATUS       obsolete
    SYNTAX       OBJECT IDENTIFIER

VariablePointer ::= TEXTUAL-CONVENTION
    STATUS       current
    SYNTAX       OBJECT IDENTIFIER

RowPointer ::= TEXTUAL-CONVENTION
    STATUS       current
    SYNTAX       OBJECT IDENTIFIER

RowStatus ::= TEXTUAL-CONVENTION
    STATUS       current
    SYNTAX       INTEGER {
                 active(1),
                 notInService(2),
                 notReady(3),
                 createAndGo(4),
                 createAndWait(5),
                 destroy(6)
               }

TimeStamp ::= TEXTUAL-CONVENTION
    STATUS       current
    SYNTAX       TimeTicks

TimeInterval ::= TEXTUAL-CONVENTION
    STATUS       current
    SYNTAX       INTEGER

DateAndTime ::= TEXTUAL-CONVENTION
    DISPLAY-HINT "2d-1d-1d,1d:1d:1d.1d,1a1d:1d"
    STATUS       current
    SYNTAX       OCTET STRING

StorageType ::= TEXTUAL-CONVENTION
    STATUS       current
    SYNTAX       INTEGER {
                 other(1),
                 volatile(2),
                 nonVolatile(3),
                 permanent(4),
                 readOnly(5)
               }

TDomain ::= TEXTUAL-CONVENTION
    STATUS       current
    SYNTAX       OBJECT IDENTIFIER

TAddress ::= TEXTUAL-CONVENTION
    STATUS       current
    SYNTAX       OCTET STRING

END
