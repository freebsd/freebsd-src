SNMPv2-PARTY-MIB DEFINITIONS ::= BEGIN

          IMPORTS
              MODULE-IDENTITY, OBJECT-TYPE, snmpModules,
                  UInteger32
                  FROM SNMPv2-SMI
              TEXTUAL-CONVENTION, RowStatus, TruthValue
                  FROM SNMPv2-TC
              MODULE-COMPLIANCE, OBJECT-GROUP
                  FROM SNMPv2-CONF;

          partyMIB MODULE-IDENTITY
              LAST-UPDATED "9304010000Z"
              ORGANIZATION "IETF SNMP Security Working Group"
              CONTACT-INFO
                      "        Keith McCloghrie

                       Postal: Hughes LAN Systems
                               1225 Charleston Road
                               Mountain View, CA  94043
                               US

                          Tel: +1 415 966 7934
                          Fax: +1 415 960 3738

                       E-mail: kzm@hls.com"
              ::= { snmpModules 3 }



          Party ::= TEXTUAL-CONVENTION
              STATUS       current
              SYNTAX       OBJECT IDENTIFIER

          TAddress ::= TEXTUAL-CONVENTION
              STATUS       current
              SYNTAX       OCTET STRING


          Clock ::= TEXTUAL-CONVENTION
              STATUS       current
              SYNTAX       UInteger32

          Context ::= TEXTUAL-CONVENTION
              STATUS       current
              SYNTAX       OBJECT IDENTIFIER


          StorageType ::= TEXTUAL-CONVENTION
              STATUS       current
              SYNTAX       INTEGER {
                           }



          partyAdmin     OBJECT IDENTIFIER ::= { partyMIB 1 }


          partyProtocols OBJECT IDENTIFIER ::= { partyAdmin 1 }

          noAuth         OBJECT IDENTIFIER ::= { partyProtocols 1 }

          noPriv         OBJECT IDENTIFIER ::= { partyProtocols 2 }

          desPrivProtocol
                         OBJECT IDENTIFIER ::= { partyProtocols 3 }

          v2md5AuthProtocol
                         OBJECT IDENTIFIER ::= { partyProtocols 4 }


          temporalDomains
                         OBJECT IDENTIFIER ::= { partyAdmin 2 }

          currentTime    OBJECT IDENTIFIER ::= { temporalDomains 1 }

          restartTime    OBJECT IDENTIFIER ::= { temporalDomains 2 }

          cacheTime      OBJECT IDENTIFIER ::= { temporalDomains 3 }




          initialPartyId OBJECT IDENTIFIER ::= { partyAdmin 3 }

          initialContextId
                         OBJECT IDENTIFIER ::= { partyAdmin 4 }






































          partyMIBObjects
                         OBJECT IDENTIFIER ::= { partyMIB 2 }


          snmpParties    OBJECT IDENTIFIER ::= { partyMIBObjects 1 }

          partyTable OBJECT-TYPE
              SYNTAX      SEQUENCE OF PartyEntry
              MAX-ACCESS  not-accessible
              STATUS      current
              ::= { snmpParties 1 }

          partyEntry OBJECT-TYPE
              SYNTAX      PartyEntry
              MAX-ACCESS  not-accessible
              STATUS      current
              INDEX      { IMPLIED partyIdentity }
              ::= { partyTable 1 }


          PartyEntry ::=
              SEQUENCE {
                  partyIdentity        Party,
                  partyIndex           INTEGER,
                  partyTDomain         OBJECT IDENTIFIER,
                  partyTAddress        TAddress,
                  partyMaxMessageSize  INTEGER,
                  partyLocal           TruthValue,
                  partyAuthProtocol    OBJECT IDENTIFIER,
                  partyAuthClock       Clock,
                  partyAuthPrivate     OCTET STRING,
                  partyAuthPublic      OCTET STRING,
                  partyAuthLifetime    INTEGER,
                  partyPrivProtocol    OBJECT IDENTIFIER,
                  partyPrivPrivate     OCTET STRING,
                  partyPrivPublic      OCTET STRING,
                  partyCloneFrom       Party,
                  partyStorageType     StorageType,
                  partyStatus          RowStatus
              }

          partyIdentity OBJECT-TYPE
              SYNTAX      Party
              MAX-ACCESS  not-accessible
              STATUS      current
              ::= { partyEntry 1 }

          partyIndex OBJECT-TYPE
              SYNTAX      INTEGER (1..65535)
              MAX-ACCESS  read-only
              STATUS      current
              ::= { partyEntry 2 }


          partyTDomain OBJECT-TYPE
              SYNTAX      OBJECT IDENTIFIER
              MAX-ACCESS  read-create
              STATUS      current
              DEFVAL      { snmpUDPDomain }
              ::= { partyEntry 3 }

          partyTAddress OBJECT-TYPE
              SYNTAX      TAddress
              MAX-ACCESS  read-create
              STATUS      current
              DEFVAL      { '000000000000'H }
              ::= { partyEntry 4 }

          partyMaxMessageSize OBJECT-TYPE
              SYNTAX      INTEGER (484..65507)
              MAX-ACCESS  read-create
              STATUS      current
              DEFVAL      { 484 }
              ::= { partyEntry 5 }


          partyLocal OBJECT-TYPE
              SYNTAX      TruthValue
              MAX-ACCESS  read-create
              STATUS      current
              DEFVAL      { false }
              ::= { partyEntry 6 }

          partyAuthProtocol OBJECT-TYPE
              SYNTAX      OBJECT IDENTIFIER
              MAX-ACCESS  read-create
              STATUS      current
              DEFVAL      { v2md5AuthProtocol }
              ::= { partyEntry 7 }


          partyAuthClock OBJECT-TYPE
              SYNTAX      Clock
              MAX-ACCESS  read-create
              STATUS      current
              DEFVAL      { 0 }
              ::= { partyEntry 8 }


          partyAuthPrivate OBJECT-TYPE
              SYNTAX      OCTET STRING
              MAX-ACCESS  read-create
              STATUS      current
              ::= { partyEntry 9 }


          partyAuthPublic OBJECT-TYPE
              SYNTAX      OCTET STRING
              MAX-ACCESS  read-create
              STATUS      current
              ::= { partyEntry 10 }


          partyAuthLifetime OBJECT-TYPE
              SYNTAX      INTEGER (0..2147483647)
              UNITS       "seconds"
              MAX-ACCESS  read-create
              STATUS      current
              DEFVAL      { 300 }
              ::= { partyEntry 11 }

          partyPrivProtocol OBJECT-TYPE
              SYNTAX      OBJECT IDENTIFIER
              MAX-ACCESS  read-create
              STATUS      current
              DEFVAL      { noPriv }
              ::= { partyEntry 12 }


          partyPrivPrivate OBJECT-TYPE
              SYNTAX      OCTET STRING
              MAX-ACCESS  read-create
              STATUS      current
              ::= { partyEntry 13 }


          partyPrivPublic OBJECT-TYPE
              SYNTAX      OCTET STRING
              MAX-ACCESS  read-create
              STATUS      current
              ::= { partyEntry 14 }


          partyCloneFrom OBJECT-TYPE
              SYNTAX      Party
              MAX-ACCESS  read-create
              STATUS      current
              ::= { partyEntry 15 }


          partyStorageType OBJECT-TYPE
              SYNTAX      StorageType
              MAX-ACCESS  read-create
              STATUS      current
              DEFVAL      { nonVolatile }
              ::= { partyEntry 16 }

          partyStatus OBJECT-TYPE
              SYNTAX      RowStatus
              MAX-ACCESS  read-create
              STATUS      current
              ::= { partyEntry 17 }



          snmpContexts   OBJECT IDENTIFIER ::= { partyMIBObjects 2 }

          contextTable OBJECT-TYPE
              SYNTAX      SEQUENCE OF ContextEntry
              MAX-ACCESS  not-accessible
              STATUS      current
              ::= { snmpContexts 1 }

          contextEntry OBJECT-TYPE
              SYNTAX      ContextEntry
              MAX-ACCESS  not-accessible
              STATUS      current
              INDEX      { IMPLIED contextIdentity }
              ::= { contextTable 1 }

          ContextEntry ::=
              SEQUENCE {
                  contextIdentity         Context,
                  contextIndex            INTEGER,
                  contextLocal            TruthValue,
                  contextViewIndex        INTEGER,
                  contextLocalEntity      OCTET STRING,
                  contextLocalTime        OBJECT IDENTIFIER,
                  contextProxyDstParty    Party,
                  contextProxySrcParty    Party,
                  contextProxyContext     OBJECT IDENTIFIER,
                  contextStorageType      StorageType,
                  contextStatus           RowStatus
              }


          contextIdentity OBJECT-TYPE
              SYNTAX      Context
              MAX-ACCESS  not-accessible
              STATUS      current
              ::= { contextEntry 1 }

          contextIndex OBJECT-TYPE
              SYNTAX      INTEGER (1..65535)
              MAX-ACCESS  read-only
              STATUS      current
              ::= { contextEntry 2 }

          contextLocal OBJECT-TYPE
              SYNTAX      TruthValue
              MAX-ACCESS  read-create
              STATUS      current
              DEFVAL      { true }
              ::= { contextEntry 3 }


          contextViewIndex OBJECT-TYPE
              SYNTAX      INTEGER (0..65535)
              MAX-ACCESS  read-create
              STATUS      current
              ::= { contextEntry 4 }


          contextLocalEntity OBJECT-TYPE
              SYNTAX      OCTET STRING
              MAX-ACCESS  read-create
              STATUS      current
              ::= { contextEntry 5 }

          contextLocalTime OBJECT-TYPE
              SYNTAX      OBJECT IDENTIFIER
              MAX-ACCESS  read-create
              STATUS      current
              DEFVAL      { currentTime }
              ::= { contextEntry 6 }


          contextProxyDstParty OBJECT-TYPE
              SYNTAX      Party
              MAX-ACCESS  read-create
              STATUS      current
              ::= { contextEntry 7 }

          contextProxySrcParty OBJECT-TYPE
              SYNTAX      Party
              MAX-ACCESS  read-create
              STATUS      current
              ::= { contextEntry 8 }


          contextProxyContext OBJECT-TYPE
              SYNTAX      OBJECT IDENTIFIER
              MAX-ACCESS  read-create
              STATUS      current
              ::= { contextEntry 9 }

          contextStorageType OBJECT-TYPE
              SYNTAX      StorageType
              MAX-ACCESS  read-create
              STATUS      current
              DEFVAL      { nonVolatile }
              ::= { contextEntry 10 }


          contextStatus OBJECT-TYPE
              SYNTAX      RowStatus
              MAX-ACCESS  read-create
              STATUS      current
              ::= { contextEntry 11 }



          snmpAccess     OBJECT IDENTIFIER ::= { partyMIBObjects 3 }

          aclTable OBJECT-TYPE
              SYNTAX      SEQUENCE OF AclEntry
              MAX-ACCESS  not-accessible
              STATUS      current
              ::= { snmpAccess 1 }

          aclEntry OBJECT-TYPE
              SYNTAX      AclEntry
              MAX-ACCESS  not-accessible
              STATUS      current
              INDEX      { aclTarget, aclSubject, aclResources }
              ::= { aclTable 1 }

          AclEntry ::=
              SEQUENCE {
                  aclTarget        INTEGER,
                  aclSubject       INTEGER,
                  aclResources     INTEGER,
                  aclPrivileges    INTEGER,
                  aclStorageType   StorageType,
                  aclStatus        RowStatus
              }


          aclTarget OBJECT-TYPE
              SYNTAX      INTEGER (1..65535)
              MAX-ACCESS  not-accessible
              STATUS      current
              ::= { aclEntry 1 }

          aclSubject OBJECT-TYPE
              SYNTAX      INTEGER (1..65535)
              MAX-ACCESS  not-accessible
              STATUS      current
              ::= { aclEntry 2 }

          aclResources OBJECT-TYPE
              SYNTAX      INTEGER (1..65535)
              MAX-ACCESS  not-accessible
              STATUS      current
              ::= { aclEntry 3 }


          aclPrivileges OBJECT-TYPE
              SYNTAX      INTEGER (0..255)
              MAX-ACCESS  read-create
              STATUS      current
              ::= { aclEntry 4 }

          aclStorageType OBJECT-TYPE
              SYNTAX      StorageType
              MAX-ACCESS  read-create
              STATUS      current
              DEFVAL      { nonVolatile }
              ::= { aclEntry 5 }


          aclStatus OBJECT-TYPE
              SYNTAX      RowStatus
              MAX-ACCESS  read-create
              STATUS      current
              ::= { aclEntry 6 }



          snmpViews      OBJECT IDENTIFIER ::= { partyMIBObjects 4 }

          viewTable OBJECT-TYPE
              SYNTAX      SEQUENCE OF ViewEntry
              MAX-ACCESS  not-accessible
              STATUS      current
              ::= { snmpViews 1 }

          viewEntry OBJECT-TYPE
              SYNTAX      ViewEntry
              MAX-ACCESS  not-accessible
              STATUS      current
              INDEX      { viewIndex, IMPLIED viewSubtree }
              ::= { viewTable 1 }

          ViewEntry ::=
              SEQUENCE {
                  viewIndex        INTEGER,
                  viewSubtree      OBJECT IDENTIFIER,
                  viewMask         OCTET STRING,
                  viewType         INTEGER,
                  viewStorageType  StorageType,
                  viewStatus       RowStatus
              }


          viewIndex OBJECT-TYPE
              SYNTAX      INTEGER (1..65535)
              MAX-ACCESS  not-accessible
              STATUS      current
              ::= { viewEntry 1 }

          viewSubtree OBJECT-TYPE
              SYNTAX      OBJECT IDENTIFIER
              MAX-ACCESS  not-accessible
              STATUS      current
              ::= { viewEntry 2 }

          viewMask OBJECT-TYPE
              SYNTAX      OCTET STRING (SIZE (0..16))
              MAX-ACCESS  read-create
              STATUS      current
              DEFVAL      { ''H }
              ::= { viewEntry 3 }


          viewType OBJECT-TYPE
              SYNTAX      INTEGER  {
                              included(1),
                              excluded(2)
                          }
              MAX-ACCESS  read-create
              STATUS      current
              DEFVAL      { included }
              ::= { viewEntry 4 }

          viewStorageType OBJECT-TYPE
              SYNTAX      StorageType
              MAX-ACCESS  read-create
              STATUS      current
              DEFVAL      { nonVolatile }
              ::= { viewEntry 5 }

          viewStatus OBJECT-TYPE
              SYNTAX      RowStatus
              MAX-ACCESS  read-create
              STATUS      current
              ::= { viewEntry 6 }



          partyMIBConformance
                         OBJECT IDENTIFIER ::= { partyMIB 3 }

          partyMIBCompliances
                         OBJECT IDENTIFIER ::= { partyMIBConformance 1 }
          partyMIBGroups
                         OBJECT IDENTIFIER ::= { partyMIBConformance 2 }


          unSecurableCompliance MODULE-COMPLIANCE
              STATUS  current
                  MANDATORY-GROUPS { partyMIBGroup }
              ::= { partyMIBCompliances 1 }

          partyNoPrivacyCompliance MODULE-COMPLIANCE
              STATUS  current
                  MANDATORY-GROUPS { partyMIBGroup }
              ::= { partyMIBCompliances 2 }


          partyPrivacyCompliance MODULE-COMPLIANCE
              STATUS  current
                  MANDATORY-GROUPS { partyMIBGroup }
              ::= { partyMIBCompliances 3 }


          fullPrivacyCompliance MODULE-COMPLIANCE
              STATUS  current
                  MANDATORY-GROUPS { partyMIBGroup }
              ::= { partyMIBCompliances 4 }


        partyMIBGroup OBJECT-GROUP
            OBJECTS { partyIndex, partyTDomain, partyTAddress,
                      partyMaxMessageSize, partyLocal,
                      partyAuthProtocol, partyAuthClock,
                      partyAuthPrivate, partyAuthPublic,
                      partyAuthLifetime, partyPrivProtocol,
                      partyPrivPrivate, partyPrivPublic,
                      partyStorageType, partyStatus,
                      partyCloneFrom,
                      contextIndex, contextLocal,
                      contextViewIndex, contextLocalEntity,
                      contextLocalTime, contextStorageType,
                      contextStatus, aclTarget, aclSubject,
                      aclPrivileges, aclStorageType, aclStatus,
                      viewMask, viewType, viewStorageType, viewStatus }
            STATUS  current
            ::= { partyMIBGroups 1 }

END
