UCD-SNMP-MIB DEFINITIONS ::= BEGIN


IMPORTS
        enterprises, OBJECT-TYPE 				
	    FROM SNMPv2-SMI
	DisplayString 				
	    FROM SNMPv2-TC;

ucdavis          OBJECT IDENTIFIER ::= { enterprises 2021 }


ucdSnmpAgent      OBJECT IDENTIFIER ::= { ucdavis 250 }
hpux9             OBJECT IDENTIFIER ::= { ucdSnmpAgent 1 }
hpux10            OBJECT IDENTIFIER ::= { ucdSnmpAgent 6 }
sunos4            OBJECT IDENTIFIER ::= { ucdSnmpAgent 2 }
solaris           OBJECT IDENTIFIER ::= { ucdSnmpAgent 3 }
osf               OBJECT IDENTIFIER ::= { ucdSnmpAgent 4 }
ultrix            OBJECT IDENTIFIER ::= { ucdSnmpAgent 5 }
netbsd1           OBJECT IDENTIFIER ::= { ucdSnmpAgent 7 }
freebsd2          OBJECT IDENTIFIER ::= { ucdSnmpAgent 8 }
irix              OBJECT IDENTIFIER ::= { ucdSnmpAgent 9 }
unknown           OBJECT IDENTIFIER ::= { ucdSnmpAgent 255 }


processes OBJECT-TYPE
	SYNTAX Processes
	ACCESS not-accessible
	STATUS mandatory
	INDEX { processIndex }
	::= { ucdavis 1 }


Processes ::= SEQUENCE {
   processIndex  INTEGER,
   processNames  DisplayString,
   processMin    INTEGER,
   processMax    INTEGER,
   processCount  INTEGER,
   processErrorFlag  INTEGER,
   processErrMessage  DisplayString,
   processErrFix  INTEGER
}

processIndex OBJECT-TYPE
	SYNTAX INTEGER
	ACCESS read-only
	STATUS mandatory
	::= { processes 1 }

processNames OBJECT-TYPE
	SYNTAX DisplayString  (SIZE (0..255))
	ACCESS read-only
	STATUS mandatory
	::= { processes 2 }

processMin OBJECT-TYPE
	SYNTAX INTEGER
	ACCESS read-only
	STATUS mandatory
	::= { processes 3 }

processMax OBJECT-TYPE
	SYNTAX INTEGER
	ACCESS read-only
	STATUS mandatory
	::= { processes 4 }

processCount OBJECT-TYPE
	SYNTAX INTEGER
	ACCESS read-only
	STATUS mandatory
	::= { processes 5 }

processErrorFlag OBJECT-TYPE
	SYNTAX INTEGER
	ACCESS read-only
	STATUS mandatory
	::= { processes 100 }

processErrMessage OBJECT-TYPE
	SYNTAX DisplayString  (SIZE (0..255))
	ACCESS read-only
	STATUS mandatory
	::= { processes 101 }

processErrFix OBJECT-TYPE
	SYNTAX INTEGER
	ACCESS read-write
	STATUS mandatory
	::= { processes 102 }

extensible OBJECT-TYPE
	SYNTAX Extensible
	ACCESS not-accessible
	STATUS mandatory
	INDEX { extensibleIndex }
	::= { ucdavis 3 }

Extensible ::= SEQUENCE {
   extensibleIndex   INTEGER,
   extensibleNames   DisplayString,
   extensibleCommand DisplayString,
   extensibleResult  INTEGER,
   extensibleOutput  DisplayString,
   extensibleErrFix  INTEGER
}

extensibleIndex OBJECT-TYPE
	SYNTAX INTEGER
	ACCESS read-only
	STATUS mandatory
	::= { extensible 1 }

extensibleNames OBJECT-TYPE
	SYNTAX DisplayString  (SIZE (0..255))
	ACCESS read-only
	STATUS mandatory
	::= { extensible 2 }

extensibleCommand OBJECT-TYPE
	SYNTAX DisplayString  (SIZE (0..255))
	ACCESS read-only
	STATUS mandatory
	::= { extensible 3 }

extensibleResult OBJECT-TYPE
	SYNTAX INTEGER
	ACCESS read-only
	STATUS mandatory
	::= { extensible 100 }

extensibleOutput OBJECT-TYPE
	SYNTAX DisplayString (SIZE (0..255))
	ACCESS read-only
	STATUS mandatory
	::= { extensible 101 }

extensibleErrFix OBJECT-TYPE
	SYNTAX INTEGER
	ACCESS read-write
	STATUS mandatory
	::= { extensible 102 }
	
memory OBJECT-TYPE
	SYNTAX Memory
	ACCESS not-accessible
	STATUS mandatory
	::= { ucdavis 4 }

Memory ::= SEQUENCE {
   memIndex        INTEGER,
   memErrorName    DisplayString,
   memTotalSwap     INTEGER,
   memAvailSwap     INTEGER,
   memTotalReal     INTEGER,
   memAvailReal     INTEGER,
   memTotalSwapTXT     INTEGER,
   memAvailSwapTXT     INTEGER,
   memTotalRealTXT     INTEGER,
   memAvailRealTXT     INTEGER,
   memTotalFree       INTEGER,
   memMinimumSwap       INTEGER,
   memSwapError       DisplayString
}
memIndex OBJECT-TYPE
     SYNTAX  INTEGER
     ACCESS  read-only
     STATUS  mandatory
     ::= { memory 1 } 

memErrorName OBJECT-TYPE
     SYNTAX  DisplayString
     ACCESS  read-only
     STATUS  mandatory
     ::= { memory 2 } 

memTotalSwap OBJECT-TYPE
	SYNTAX INTEGER
	ACCESS read-only
	STATUS mandatory
	::= { memory 3 }

memAvailSwap OBJECT-TYPE
	SYNTAX INTEGER
	ACCESS read-only
	STATUS mandatory
	::= { memory 4 }

memTotalReal OBJECT-TYPE
	SYNTAX INTEGER
	ACCESS read-only
	STATUS mandatory
	::= { memory 5 }

memAvailReal OBJECT-TYPE
	SYNTAX INTEGER
	ACCESS read-only
	STATUS mandatory
	::= { memory 6 }

memTotalSwapTXT OBJECT-TYPE
	SYNTAX INTEGER
	ACCESS read-only
	STATUS mandatory
	::= { memory 7 }

memAvailSwapTXT OBJECT-TYPE
	SYNTAX INTEGER
	ACCESS read-only
	STATUS mandatory
	::= { memory 8 }

memTotalRealTXT OBJECT-TYPE
	SYNTAX INTEGER
	ACCESS read-only
	STATUS mandatory
	::= { memory 9 }

memAvailRealTXT OBJECT-TYPE
	SYNTAX INTEGER
	ACCESS read-only
	STATUS mandatory
	::= { memory 10 }

memTotalFree OBJECT-TYPE
	SYNTAX INTEGER
	ACCESS read-only
	STATUS mandatory
	::= { memory 11 }

memMinimumSwap OBJECT-TYPE
	SYNTAX INTEGER
	ACCESS read-only
	STATUS mandatory
	::= { memory 12 }

memSwapError OBJECT-TYPE
	SYNTAX INTEGER
	ACCESS read-only
	STATUS mandatory
	::= { memory 100 }
	
memSwapErrorMsg OBJECT-TYPE
     SYNTAX  DisplayString
     ACCESS  read-only
     STATUS  mandatory
     ::= { memory 101 } 

lockd OBJECT-TYPE
	SYNTAX Lockd
	ACCESS not-accessible
	STATUS mandatory
	INDEX { lockdIndex }
	::= { ucdavis 5 }

Lockd ::= SEQUENCE {
   lockdIndex   INTEGER,
   lockdError  INTEGER,
   lockdErrorMsg  DisplayString
}

lockdIndex OBJECT-TYPE
	SYNTAX INTEGER
	ACCESS read-only
	STATUS mandatory
	::= { lockd 1 }

lockdError OBJECT-TYPE
	SYNTAX INTEGER
	ACCESS read-only
	STATUS mandatory
	::= { lockd 100 }

lockdErrorMsg OBJECT-TYPE
	SYNTAX DisplayString (SIZE (0..255))
	ACCESS read-only
	STATUS mandatory
	::= { lockd 101 }

disk 	OBJECT-TYPE
	SYNTAX Disk
	ACCESS not-accessible
	STATUS mandatory
	INDEX { diskIndex }
	::= { ucdavis 6 }

Disk ::= SEQUENCE {
   diskIndex   INTEGER,
   diskPath  DisplayString,
   diskDevice  DisplayString,
   diskMinimum  INTEGER,
   diskTotal  INTEGER,
   diskAvail  INTEGER,
   diskUsed  INTEGER,
   diskPercent  INTEGER,
   diskErrorFlag  INTEGER,
   diskErrorMsg  DisplayString
}

diskIndex OBJECT-TYPE
	SYNTAX INTEGER
	ACCESS read-only
	STATUS mandatory
	::= { disk 1 }
	
diskPath OBJECT-TYPE
     SYNTAX  DisplayString
     ACCESS  read-only
     STATUS  mandatory
     ::= { disk 2 } 

diskDevice OBJECT-TYPE
     SYNTAX  DisplayString
     ACCESS  read-only
     STATUS  mandatory
     ::= { disk 3 } 

diskMinimum OBJECT-TYPE
     SYNTAX  INTEGER
     ACCESS  read-only
     STATUS  mandatory
     ::= { disk 4 } 

diskTotal OBJECT-TYPE
     SYNTAX  INTEGER
     ACCESS  read-only
     STATUS  mandatory
     ::= { disk 5 } 

diskAvail OBJECT-TYPE
     SYNTAX  INTEGER
     ACCESS  read-only
     STATUS  mandatory
     ::= { disk 6 } 

diskUsed OBJECT-TYPE
     SYNTAX  INTEGER
     ACCESS  read-only
     STATUS  mandatory
     ::= { disk 7 } 

diskPercent OBJECT-TYPE
     SYNTAX  INTEGER
     ACCESS  read-only
     STATUS  mandatory
     ::= { disk 8 } 

diskErrorFlag OBJECT-TYPE
     SYNTAX  INTEGER
     ACCESS  read-only
     STATUS  mandatory
     ::= { disk 100 } 
     
diskErrorMsg OBJECT-TYPE
     SYNTAX  DisplayString
     ACCESS  read-only
     STATUS  mandatory
     ::= { disk 101 } 
     
loadaves OBJECT-TYPE
	SYNTAX Loadaves
	ACCESS not-accessible
	STATUS mandatory
	INDEX { loadaveIndex }
	::= { ucdavis 7 }


Loadaves ::= SEQUENCE {
   loadaveIndex  INTEGER,
   loadaveNames  DisplayString,
   loadaveLoad   DisplayString,
   loadaveConfig DisplayString,
   loadaveErrorFlag  INTEGER,
   loadaveErrMessage  DisplayString
}

loadaveIndex OBJECT-TYPE
	SYNTAX INTEGER
	ACCESS read-only
	STATUS mandatory
	::= { loadaves 1 }

loadaveNames OBJECT-TYPE
	SYNTAX DisplayString (SIZE (0..255))
	ACCESS read-only
	STATUS mandatory
	::= { loadaves 2 }

loadaveLoad OBJECT-TYPE
	SYNTAX DisplayString
	ACCESS read-only
	STATUS mandatory
	::= { loadaves 3 }

loadaveConfig OBJECT-TYPE
	SYNTAX DisplayString
	ACCESS read-only
	STATUS mandatory
	::= { loadaves 4 }

loadaveErrorFlag OBJECT-TYPE
	SYNTAX INTEGER
	ACCESS read-only
	STATUS mandatory
	::= { loadaves 100 }

loadaveErrMessage OBJECT-TYPE
	SYNTAX DisplayString (SIZE (0..255))
	ACCESS read-only
	STATUS mandatory
	::= { loadaves 101 }

version	OBJECT-TYPE
	SYNTAX Version
	ACCESS not-accessible
	STATUS mandatory
	INDEX { versionIndex }
	::= { ucdavis 100 }

Version ::= SEQUENCE {
   versionIndex   INTEGER,
   versionTag  DisplayString,
   versionDate  DisplayString,
   versionCDate  DisplayString,
   versionIdent  DisplayString,
   versionClearCache  INTEGER,
   versionUpdateConfig  INTEGER
}
   
versionIndex OBJECT-TYPE
     SYNTAX  INTEGER
     ACCESS  read-only
     STATUS  mandatory
     ::= { version 1 } 

versionTag OBJECT-TYPE
     SYNTAX  DisplayString
     ACCESS  read-only
     STATUS  mandatory
     ::= { version 2 } 
     
versionDate OBJECT-TYPE
     SYNTAX  DisplayString
     ACCESS  read-only
     STATUS  mandatory
     ::= { version 3 } 

versionCDate OBJECT-TYPE
     SYNTAX  DisplayString
     ACCESS  read-only
     STATUS  mandatory
     ::= { version 4 } 

versionIdent OBJECT-TYPE
     SYNTAX  DisplayString
     ACCESS  read-only
     STATUS  mandatory
     ::= { version 5 } 

versionClearCache OBJECT-TYPE
     SYNTAX  INTEGER
     ACCESS  read-write
     STATUS  mandatory
     ::= { version 10 } 

versionUpdateConfig OBJECT-TYPE
     SYNTAX  INTEGER
     ACCESS  read-write
     STATUS  mandatory
     ::= { version 11 } 

versionRestartAgent OBJECT-TYPE
     SYNTAX  INTEGER
     ACCESS  read-write
     STATUS  mandatory
     ::= { version 12 } 

snmperrs OBJECT-TYPE
	SYNTAX Snmperrs
	ACCESS not-accessible
	STATUS mandatory
	INDEX { snmperrIndex }
	::= { ucdavis 101 }


Snmperrs ::= SEQUENCE {
   snmperrIndex  INTEGER,
   snmperrNames  DisplayString,
   snmperrErrorFlag  INTEGER,
   snmperrErrMessage  DisplayString
}

snmperrIndex OBJECT-TYPE
	SYNTAX INTEGER
	ACCESS read-only
	STATUS mandatory
	::= { snmperrs 1 }

snmperrNames OBJECT-TYPE
	SYNTAX DisplayString (SIZE (0..255))
	ACCESS read-only
	STATUS mandatory
	::= { snmperrs 2 }

snmperrErrorFlag OBJECT-TYPE
	SYNTAX INTEGER
	ACCESS read-only
	STATUS mandatory
	::= { snmperrs 100 }

snmperrErrMessage OBJECT-TYPE
	SYNTAX DisplayString (SIZE (0..255))
	ACCESS read-only
	STATUS mandatory
	::= { snmperrs 101 }

END
