SNMPv2-SMI DEFINITIONS ::= BEGIN

org ::= { iso  3 }

dod ::= { org  6 }

internet ::= { dod  1 }

directory ::= { internet  1 }

mgmt ::= { internet  2 }

mib-2 ::= { mgmt  1 }

transmission ::= { mib-2  10 }

experimental ::= { internet  3 }

private ::= { internet  4 }

enterprises ::= { private  1 }

security ::= { internet  5 }

snmpV2 ::= { internet  6 }

snmpDomains ::= { snmpV2  1 }

snmpProxys ::= { snmpV2  2 }

snmpModules ::= { snmpV2  3 }

ObjectName ::=
    OBJECT IDENTIFIER

NotificationName ::=
    OBJECT IDENTIFIER












zeroDotZero OBJECT-IDENTITY
    STATUS       current
    ::= { 0  0 }

END
