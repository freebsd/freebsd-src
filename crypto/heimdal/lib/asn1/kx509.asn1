-- $Id: kx509.asn1 19546 2006-12-28 21:05:23Z lha $

KX509 DEFINITIONS ::=
BEGIN

Kx509Request ::= SEQUENCE {
	authenticator OCTET STRING,
	pk-hash OCTET STRING,
	pk-key OCTET STRING
}

Kx509Response ::= SEQUENCE {
	error-code[0]	INTEGER (-2147483648..2147483647)
	      OPTIONAL -- DEFAULT 0 --,
	hash[1]		OCTET STRING OPTIONAL,
	certificate[2]	OCTET STRING OPTIONAL,
	e-text[3]	VisibleString OPTIONAL
}

END
