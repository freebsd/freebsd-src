--
-- Copyright (c) 2001-2003
--	Fraunhofer Institute for Open Communication Systems (FhG Fokus).
--	All rights reserved.
--
-- Author: Harti Brandt <harti@freebsd.org>
--
-- Redistribution and use in source and binary forms, with or without
-- modification, are permitted provided that the following conditions
-- are met:
-- 1. Redistributions of source code must retain the above copyright
--    notice, this list of conditions and the following disclaimer.
-- 2. Redistributions in binary form must reproduce the above copyright
--    notice, this list of conditions and the following disclaimer in the
--    documentation and/or other materials provided with the distribution.
--
-- THIS SOFTWARE IS PROVIDED BY AUTHOR AND CONTRIBUTORS ``AS IS'' AND
-- ANY EXPRESS OR IMPLIED WARRANTIES, INCLUDING, BUT NOT LIMITED TO, THE
-- IMPLIED WARRANTIES OF MERCHANTABILITY AND FITNESS FOR A PARTICULAR PURPOSE
-- ARE DISCLAIMED.  IN NO EVENT SHALL AUTHOR OR CONTRIBUTORS BE LIABLE
-- FOR ANY DIRECT, INDIRECT, INCIDENTAL, SPECIAL, EXEMPLARY, OR CONSEQUENTIAL
-- DAMAGES (INCLUDING, BUT NOT LIMITED TO, PROCUREMENT OF SUBSTITUTE GOODS
-- OR SERVICES; LOSS OF USE, DATA, OR PROFITS; OR BUSINESS INTERRUPTION)
-- HOWEVER CAUSED AND ON ANY THEORY OF LIABILITY, WHETHER IN CONTRACT, STRICT
-- LIABILITY, OR TORT (INCLUDING NEGLIGENCE OR OTHERWISE) ARISING IN ANY WAY
-- OUT OF THE USE OF THIS SOFTWARE, EVEN IF ADVISED OF THE POSSIBILITY OF
-- SUCH DAMAGE.
--
-- Fokus PEN root module.
--
FOKUS-MIB DEFINITIONS ::= BEGIN

IMPORTS
    MODULE-IDENTITY, enterprises
	FROM SNMPv2-SMI;

fokus MODULE-IDENTITY
    LAST-UPDATED "202304140000Z"
    ORGANIZATION "Fraunhofer FOKUS"
    CONTACT-INFO
	    "		Bjoern Riemer

	     Postal:	Fraunhofer Institute for Open Communication Systems
			Kaiserin-Augusta-Allee 31
			10589 Berlin
			Germany

	     E-mail:	iana-pen@fokus.fraunhofer.de"
    DESCRIPTION
	    "The root of the Fokus enterprises tree."
    REVISION "202304140000Z"
    DESCRIPTION
	    "Contact info updated."
    REVISION "200202050000Z"
    DESCRIPTION
	    "Initial revision."
    ::= { enterprises 12325 }

--
-- begemot ::= fokus.1
--	contact: hartmut.brandt@dlr.de
--
END
